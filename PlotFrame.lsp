;;; ============================================================
;;; PlotFrame.lsp v1.13 — МОНОЛИТ (сборка трёх модулей + фаза 2;
;;; ранее файл назывался PlotFrameBundle.lsp). Загружать ВМЕСТО
;;; трёх старых файлов из archive/, НЕ вместе с ними: имена
;;; команд те же.
;;;   секция 1: PlotSPDSToPDF.lsp  v0.85 (СПДС -> PDF, ПСПНАСТРОЙКИ)
;;;   секция 2: PlotFrameToPDF.lsp v3.27 (рамки -> PDF, ЭКСПДФ)
;;;   секция 3: PlotFrameToFP.lsp  v1.03 (рамки -> принтер, ЭКСФПА4/A3)
;;;   секция 4: ЭКССПДСФП — форматы СПДС на системный принтер
;;; v1.13: ДВЕ ошибки v1.11/v1.12: (1) префикс формат-группы об-
;;;        рывался на символ (vl-string-search даёт 0-based «_(»,
;;;        префикс = substr 1 k, а не (1- k)): «2A0» -> «2A», сопос-
;;;        тавление не работало никогда; (2) «Перевернуть?» — это
;;;        180°, ориентацию на книжной бумаге (2A0/A0 только книж-
;;;        ные у pc3) задаёт САМ слот _L/_P по рамке — механизм «раз-
;;;        ворота» удалён, слот снова «_N». Факт — в логе и отчёте.
;;; v1.12: psp-page-preset: ПОРЯДОК — сначала put ConfigName (pc3),
;;;        ЗАТЕМ GetCanonicalMediaNames. Причина провала 1.11: спи-
;;;        сок брали у старого устройства (FinePrint — без ISO_*),
;;;        want=nil, бумага не ставилась, все листы ушли в дефолт
;;;        ANSI_A. Проверка порядка: диагностический сниппет юзера
;;;        (put перед списком) работал верно.
;;; v1.11: psp-page-preset: имя бумаги ставится ТОЛЬКО если оно
;;;        есть в списке бумаг устройства (точное или та же формат-
;;;        группа); нехватка альбомной ориентации (2A0/A0 у pc3 толь-
;;;        ко книжные) компенсируется разворотом чертежа в ленте
;;;        («Перевернуть?» = Да, *psp-rot-adj*). Причина: подстановка
;;;        отвергнутых имён даёт хаотичный выбор бумаги AutoCAD'ом
;;;        (наблюдалось A2/ANSI_A/A0 на один и тот же запрос).
;;; v1.10: psp-page-preset (СПДС): при отказе устройства принима-
;;;        ть имя бумаги — автопоиск той же формат-группы в списке
;;;        бумаг (префикс до «_(») и подстановка существующей ориен-
;;;        тации. Причина: у pc3 DWG To PDF у 2A0/A0 полноблочные
;;;        имена только книжные -> запрошенные альбомные отвергались,
;;;        лист оставался на старой бумаге (A2/ANSI_A) и лист альбо-
;;;        ма выходил некорректным. Отчёт теперь показывает ФАКТИ-
;;;        ЧЕСКУЮ бумагу (chk), а не запрошенную.
;;; v1.09: ПСПНАСТРОЙКИ, Apply: убраны три guard-проверки
;;;        (boundp 'c:ЭКСПДФ) — легаси трёхфайловой эпохи; в моноли-
;;;        те секция базы загружена всегда, поэтому *pfp-* перемен-
;;;        ные (папка, цвет+CTB, качество) применяются БЕЗУСЛОВНО
;;;        теми же значениями. Причина: CHKALL ругался на цитиро-
;;;        ванный не-ANSI-символ 'c:ЭКСПДФ вне defun (строки
;;;        1980/2001/2021). Поведение Apply не менялось (guard все-
;;;        гда был истинен). ОТКАТ: вернуть три (if (boundp …) …)
;;;        и удалить три безусловных setq *pfp-*.
;;; v1.08: баннеры секций («Загружено: PlotSPDSToPDF/…/FP»)
;;;        УБРАНЫ — при загрузке печатается только баннер монолита;
;;;        при сбое AutoCAD сам печатает ошибку у проблемной формы.
;;; v1.07: таблица команд в баннере — в рамке (линии сверху/сни-
;;;        зу), колонки уже; хвостовое эхо «C:EXPSPDSFP» при загруз-
;;;        ке подавлено (princ в конце файла).
;;; v1.06: сокращение служебных команд (УДАЛЕНЫ: ПСПКАЧ/PSPQUAL,
;;;        ПФПЦВЕТ, ПФПЧБ, ПСПЛЕНТА/PSPTAPE, ПФПЛЕНТА/PFPTAPE,
;;;        ФПЛЕНТА/FPTAPE, ПФПМЕДИА, ПФПСТАТ, ПФПТАБЛ, ПСППАПКА/
;;;        PSPPAPKA); баннер загрузки — таблица основных команд
;;;        и краткая логика; загрузочный вывод секций — по строке.
;;; v1.05: переименование команд печати (старые имена УБРАНЫ):
;;;        ЭКССПДСВПДФ -> ЭКССПДСПДФ (SPDSTOPDF -> EXPSPDSPDF),
;;;        ЭКСВПДФ -> ЭКСПДФ (EXPTPDF -> EXPPDF),
;;;        ЭКСВПФПА4 -> ЭКСФПА4 (EXPTFPA4 -> EXPFPA4),
;;;        ЭКСВПФПА3 -> ЭКСФПА3 (EXPTFPA3 -> EXPFPA3),
;;;        ЭКССПДСВФП -> ЭКССПДСФП (EXPSPDSTOFP -> EXPSPDSFP).
;;; v1.04: ЭКССПДСФП: предустановка бумаги по механике FP —
;;;        ConfigName = системный принтер, CanonicalMediaName =
;;;        A4/A3 с readback и поиском по списку бумаг драйвера;
;;;        печать результата («предустановка: <имя>»). Причина:
;;;        старый вызов psp-page-preset ставил PDF-принтер и имя
;;;        «A3», которого у него нет -> бумага листа оставалась
;;;        A4 -> A3-рамка печаталась вписанной в A4.
;;; v1.03: секция 4 — ЭКССПДСФП: формат рамки СПДС решает принтер
;;;        (A4 -> «Принтер A4», A3+ -> «Принтер A3»), ориентация
;;;        как у рамки, масштаб всегда «Вписать»; кратность X2/X3
;;;        поднимает формат; принтеры из ПСПНАСТРОЙКИ.
;;; v1.02: переименование PlotFrameBundle.lsp -> PlotFrame.lsp
;;;        (внутренняя переменная *pfb-ver* -> *pf-ver*).
;;; v1.01: FP-секция обновлена до 1.03 (баннер версии).
;;; ============================================================
(setq *pf-ver* "1.13")
(princ "\nЗагружено: PlotFrame.lsp v1.13 — печать рамок и форматов СПДС.")
(princ "\nОсновные команды:")
(princ "\n  +--------------------------------------------------------------+")
(princ "\n  | КОМАНДА                  | ЧТО ДЕЛАЕТ                        |")
(princ "\n  +--------------------------------------------------------------+")
(princ "\n  | ЭКССПДСПДФ (EXPSPDSPDF)  | СПДС -> один PDF (склейка)        |")
(princ "\n  | ЭКСПДФ (EXPPDF)          | рамка -> PDF (по габаритам)       |")
(princ "\n  | ЭКСФПА4 (EXPFPA4)        | рамка -> принтер A4 (FinePrint)   |")
(princ "\n  | ЭКСФПА3 (EXPFPA3)        | рамка -> принтер A3               |")
(princ "\n  | ЭКССПДСФП (EXPSPDSFP)    | СПДС -> принтеры A4/A3 (по рамке) |")
(princ "\n  | ОЧИСТПДФ                 | удалить PDF папки чертежа         |")
(princ "\n  | ПСПНАСТРОЙКИ (PSPSET)    | папка, принтеры, цвет, качество   |")
(princ "\n  +--------------------------------------------------------------+")
(princ "\nЛогика: настройки и цвет общие (ПСПНАСТРОЙКИ); формат и ориентация")
(princ "\n  берутся из рамки; печать лентой -ПЕЧАТЬ; результаты в")
(princ "\n  <вывод>\\<имя чертежа>\\ (СПДС — альбом <имя>_<дата>_<время>.pdf,")
(princ "\n  рамки — 1.pdf, 2.pdf...). Диагностика: ПСПЭХОВКЛ / ПФПЭХОВКЛ /")
(princ "\n  ФПЭХОВКЛ (эхо ленты); СПДС-диагностика — ЭКССПДСДИАГ.")
(princ "\nФайлы из archive/ НЕ загружать — команды те же.")

;;; -*- coding: windows-1251 -*-
;;; PlotSPDSToPDF.lsp
;;;
;;; Серийная печать выбранных форматов СПДС GraphiCS (SPDSFORMAT)
;;; с сортировкой по листам. Диагностика ЭКССПДСДИАГ — в файле
;;; PlotSPDSDiag.lsp (модуль 2 — загрузить ПОСЛЕ этого файла).
;;;
;;; Команды: ЭКССПДСПДФ / EXPSPDSPDF — серийный экспорт в PDF
;;;
;;; Кодировка: CP1251 (ANSI), без BOM.
;;; v0.2: GetBoundingBox через vl-catch-all-apply привязывает к символам
;;;        СЫРОЙ safearray (не variant) — незащищённый vlax-variant-value
;;;        падал с «неверный тип аргумента: variantp». Добавлен
;;;        конвертер psp-va->list (variant -> значение, safearray
;;;        проходит насквозь); разбор строки таблицы диагностики
;;;        обёрнут в перехват — один плохой объект не роняет отчёт.
;;; v0.3: по дампу подтверждено: ObjectName = mcsDbObjectFormat,
;;;        кастомных COM-свойств у объекта НЕТ — формат/лист/листов
;;;        лежат в данных примитива. Добавлен универсальный экстрактор:
;;;        текстовые группы entget (1, 3), бинарные группы (310-312)
;;;        с раскодировкой hex и извлечением читаемых строк, XRecord'ы
;;;        расширения словаря, XData. Автопоиск кандидатов формата.
;;; v0.4: по логу v0.3: у объекта нет ни словаря (HasExtensionDictionary
;;;        = 0), ни текстов в entget — данные формата СПДС держит в своей
;;;        базе. Основной канал — план Б: ТЕКСТЫ штампа в области рамки
;;;        (TEXT/MTEXT/ATTRIB по габаритам объекта, сортировка сверху
;;;        вниз). Добавлен скан текстов; XData (группы 1000+) добавлен
;;;        в экстрактор; исправлен разбор вариантов XRecord.
;;; v0.5: по логу v0.4: HasExtensionDictionary = -1 — словарь ЕСТЬ,
;;;        но XRecord'ов в нём не нашлось (COM-обход не увидел).
;;;        Добавлен глубокий обход словаря расширения через dictnext
;;;        (группа 360 entget; вложенные словари рекурсивно; XRecord'ы
;;;        читаются entget'ом напрямую). Диагностика области расширена:
;;;        все типы объектов в окне, блоки, атрибуты, тексты из
;;;        определений блоков. ПроверкаPlotSPDS: закрытый продукт,
;;;        функциональный ориентир — сортировка/имёнование/многопаг PDF.
;;; v0.6: v0.5 не загрузилась у пользователя («синтаксическая ошибка»),
;;;        хотя строгий сторонний Lisp-ридер читает файл без ошибок.
;;;        Добавлены маркеры прогресса загрузки по секциям — последний
;;;        напечатанный маркер указывает секцию со сбоем.
;;;        Новая команда ПСППАПКА — открывает папку журналов в Проводнике.
;;; v0.7: найдена и исправлена причина сбоя v0.5/v0.6: маркер секции 7
;;;        был вставлен В СЕРЕДИНУ строки комментария, его хвост
;;;        «строки (1,3,1000),» становился кодом — AutoCAD пытался
;;;        вызвать (1,3,1000) как функцию. Комментарий восстановлен.
;;; v0.8: сбой сместился в секцию 8 (большой defun диагностики).
;;;        Диагностика разбита на НЕСКОЛЬКО верхнеуровневых функций
;;;        с маркерами 8a/8b/8c между ними — следующий сбой укажет
;;;        подблок точно. (apply '+ ...) заменён на явную сумму.
;;; Маркер редакции для RELOAD: (ред. 85
;;; v0.85: рамки качества — снова В СТРОКУ, но с фиксированными
;;;        слотами 23/16/16: «Низкое/Среднее/Высокое» обеих рамок
;;;        стоят на одних вертикалях. Поле пути обёрнуто в :row,
;;;        как автосборка/задержка, — правый край пути = правому
;;;        краю полей (60 = 30+30).
;;; v0.84: таблица настроек: линии рамки совпадают по ширине со
;;;        строками (колонка = «|»+пробел+28/34) — правые «+» боль-
;;;        ше не вываливаются за вертикали строк.
;;; v0.83: поле пути — на всю внутреннюю ширину рамки (60, метка
;;;        «Папка:» убрана — есть заголовок рамки). Радиокнопки ка-
;;;        чества — вертикальной колонкой в обеих рамках, подписи
;;;        рамки в PDF без «авто»: «Низкое (-1) / Среднее / Высо-
;;;        кое (+1)» — колонки обеих рамок выровнены по вертикали.
;;; v0.82: окно — всё в рамках с единой сеткой (подписи 30 вправо,
;;;        поля 30): блок 1 «Папка сохранения» (строка 2 = подсказка
;;;        + «Обзор...»), блок 2 «Сборка и результат» (автосборка,
;;;        задержка, обе галочки). Таблица настроек — ПОЛНАЯ рамка:
;;;        вертикали до и после колонок, линии сверху/после шапки/
;;;        снизу, значения добиваются пробелами до ширины колонки.
;;; v0.81: таблица настроек — С ЯЧЕЙКАМИ (вертикальный разделитель
;;;        «|», «+» на стыке). В окне строки «CTB для ч/б/цвета»
;;;        переименованы в «Чёрно-белая печать» / «Цветная печать»;
;;;        сетка: правый край всех полей по одной линии — списки 30,
;;;        поля автосборки/задержки 30, папка(21)+Обзор(9) = 30.
;;; v0.80: окно «Настройки печати» переработано: сетка — подписи
;;;        30 знаков вправо, все списки шириной 30; принтеры PDF/A4/
;;;        A3 одной колонкой; «Цветная печать (выкл=ч/б)» заменена
;;;        парой радио «Чёрно-белая печать»/«Цветная печать»; рамки
;;;        качества переименованы («Качество печати "Рамка в PDF"…»);
;;;        «Низкое (формат в формат)» -> «Низкое (по формату)».
;;; v0.79: чат «секция N/10 загружена» УБРАН: успешная загрузка —
;;;        один баннер «Загружено: …», ошибка — AutoCAD печатает сам
;;;        у проблемной формы. Отчёт настроек после «Применить» —
;;;        ПОЛНОЙ таблицей (параметр/значение, выравнивание
;;;        psp-pad-right, подчёркивание дефисами).
;;; v0.78: после «настройки сохранены» в консоль печатается список
;;;        применённых параметров: папка, PDF-принтер, цвет+CTB,
;;;        принтеры FP (A4/A3), автосборка, задержка, открытие,
;;;        удаление, качество СПДС и рамки.
;;; v0.77: умолчание списков FP-принтеров: пустое значение реестра
;;;        (= отсутствующий ключ) больше не выбирает первый принтер
;;;        списка — всегда FinePrint.
;;; v0.76: ПСПНАСТРОЙКИ: рамочка печати на принтер (FP-модуль
;;;        ЭКСФПА4/ЭКСФПА3) — два выпадающих списка СИСТЕМНЫХ
;;;        принтеров Windows (реестр HKLM Control\Print\Printers,
;;;        полный перечень; FinePrint добавлен, если отсутствует),
;;;        отдельный для A4 и для A3; хранение AppData/PlotFrame/
;;;        FPPrinterA4/A3, умолчание FinePrint.
;;; v0.75: папка сборки — просто <имя чертежа> (без даты), альбом
;;;        внутри — по-прежнему <имя>_<дата>_<время>.pdf: повторные
;;;        сборки накапливаются в одной папке, альбомы не затирают
;;;        друг друга.
;;; v0.74: (1) папка сборки названа по чертежу, как и альбом:
;;;        <имя>_<дата>_<время> (была SPDS_<штамп>); (2) найдена
;;;        причина «склеилось 5/6 из 7»: GS создаёт файл сразу, а
;;;        дописывает ПОСЛЕДНИМ — ожидание шло по первому появлению
;;;        файла, зритель открывал НЕДОПИСАННЫЙ альбом; теперь ждём
;;;        стабилизации размера (3 одинаковых замера по 0.5 с);
;;;        (3) в логе размер каждого входа (0 байт = выпавшая
;;;        страница); (4) проверка альбома перед открытием — в LISP,
;;;        нет файла -> открывается папка сборки.
;;; v0.73: три правки открытия/склейки: (1) расширение чертежа
;;;        отрезается по верной позиции (0.72 смотрел k-1 вместо
;;;        k-3 — в имени оставалось «.dwg»); (2) перед склейкой
;;;        печатается список ОТСУТСТВУЮЩИХ входов, после — размер
;;;        альбома (диагностика «склеилось меньше листов»);
;;;        (3) если альбома нет в момент открытия — открывается
;;;        папка сборки (вместо тишины).
;;; v0.72: имя чертежа берётся из DWGNAME (с отрезанием расшире-
;;;        ния), а не DWGTITLED — тот есть флаг 0/1, из-за него
;;;        0.71 всегда давал запасное «SPDS».
;;; v0.71: склеенный альбом называется <имя чертежа>_<дата>_<время>
;;;        .pdf (DWGTITLED + штамп CDATE; несохранённый чертёж —
;;;        «SPDS»). Папка сборки осталась SPDS_<дата>_<время> — под
;;;        маску удаления L*.pdf альбом не попадает, как и раньше.
;;; v0.70: ЦВЕТ ЕДИНЫЙ ДЛЯ ОБОИХ: рамочка задачи 12 раньше писала
;;;        только *pfp-* (база), а СПДС печатает по *psp-color-mode*/
;;;        *psp-ctb-* — оставался ч/б. Теперь Apply применяет к обоим
;;;        пространствам, load-cfg подхватывает в оба, диалог читает
;;;        из *psp-* (всегда объявлены). Один источник — реестр
;;;        AppData/PlotFrame/{ColorMode,CtbMono,CtbColor}.
;;; v0.69: реестр отравлен частичным Apply 0.67 (PC3="T" — в баннере
;;;        «Принтер: T»): PC3 теперь принимается/сохраняется ТОЛЬКО
;;;        при маске *.pc3; все *psp-t-* читаются через строгую
;;;        psp-str-or (не-строка -> умолчание), setcfg значений —
;;;        через psp-s->str; сообщение об ошибке диалога печатает
;;;        ЭТАП (заполнение списков / диалог / сохранение настроек).
;;; v0.68: ПСПНАСТРОЙКИ не должна ломать печать: старт диалога и
;;;        блок «Применить» обёрнуты в vl-catch-all-apply, unload_di-
;;;        alog гарантирован при ЛЮБОМ исходе (живой диалог блокирует
;;;        -ПЕЧАТЬ — инцидент 0.67: «stringp T» + 0 из 4 листов); сам
;;;        текст ошибки печатается в консоль. psp-popup-fill игнори-
;;;        рует не-строки; перечисление .pc3/.ctb переведено на флаг
;;;        «только файлы» (1) — прежний -1 читал только ПОДПАПКИ.
;;; v0.67: задача 12 — в ПСПНАСТРОЙКИ добавлена рамочка «Цвет и
;;;        стили печати (ЭКСПДФ)» под выбором принтера: переключатель
;;;        Цветная печать (выкл = ч/б) и два выпадающих списка CTB
;;;        (для ч/б и для цвета; все .ctb из папки стилей AutoCAD,
;;;        PrinterStyleSheetDir; недоступна — monochrome/acad + теку-
;;;        щие значения). Сохранение: AppData/PlotFrame/{ColorMode,
;;;        CtbMono,CtbColor} + живое применение в загруженную базу.
;;; v0.66: задача 3 — портативный Ghostscript: в psp-find-gs добавле-
;;;        на страховая ветка GS[3.5] (<диск>:\PlotFrameToPDF\gs\bin
;;;        \gswin64c.exe, диски C:/D:/E:, папка проверяется vl-file-
;;;        directory-p). Срабатывает, когда нет ни ПСПГС, ни реестра,
;;;        ни Program Files. Распакованный gs кладётся пользователем
;;;        в D:\PlotFrameToPDF\gs (в git не попадает, .gitignore).
;;; v0.65: хвост ленты Листа: ПОСТОЯННЫХ ответов стало три («масш-
;;;        штабировать веса», «печатать лист первым», «скрывать
;;;        объекты листа»); вопрос «записать изменения в макет»
;;;        задаётся ТОЛЬКО при расхождении с сохранёнными парамет-
;;;        рами листа — под него больше нет постоянного ответа,
;;;        вместо этого: сбой ленты перехватывается и выполняется
;;;        ВТОРАЯ ПОПЫТКА с четвёртым «Нет» (alt). Феномен «_N.pdf»
;;;        в папке чертежа устранён (ответ уезжал в имя файла).
;;; v0.64: устранён nil в ленте command (защита 0.63 возвращала nil —
;;;        в ряде сборок это убивает -ПЕЧАТЬ на вопросе о формате).
;;;        Теперь: Лист — всегда «Enter» (формат уже предустановлен,
;;;        лист хранит портретный канон), Модель — фактически приняв-
;;;        шийся формат (readback), при полном провале — плановое имя.
;;; v0.63: имя формата шлётся в -ПЕЧАТЬ ТОЛЬКО когда предустановка
;;;        (psp-page-preset, ActiveX) его реально приняла — теперь
;;;        psp-page-preset ВОЗВРАЩАЕТ фактический CanonicalMediaName.
;;;        Отвергнутое листом имя (альбомный канонический на Листе,
;;;        отсутствующий размер) роняет -ПЕЧАТЬ; вместо него шлётся
;;;        «Enter» — берётся фактический формат листа.
;;; v0.62: ПЕЧАТЬ С ВКЛАДКИ ЛИСТ починена: в ленте Листа 4 ответа
;;;        «Нет» перед именем файла (масштабировать веса / лист
;;;        последним / скрывать объекты листа / НЕ записывать изменения
;;;        в макет), а формат бумаги на Листе не посылается вовсе —
;;;        он уже предустановлен (psp-page-preset), альбомное имя не
;;;        совпадает с каноническим и срывало ленту после вопроса о
;;;        формате. «Масштабировать веса» (ПСПЛЕНТА) остался только
;;;        в ветке Модели.
;;; v0.61: ПСПНАСТРОЙКИ: принтер — ВЫПАДАЮЩИЙ СПИСОК всех .pc3 из
;;;        папки конфигураций плоттеров (PrinterConfigDir; если папка
;;;        недоступна — текущий + DWG To PDF.pc3). Папка сохранения —
;;;        кнопка «Обзор...»: диалог выбора папки Windows (Shell;
;;;        без COM — сообщение и ввод вручную).
;;; v0.60: ПАПКА СОХРАНЕНИЯ теперь общая и рабочая: настроенная папка
;;;        становится *psp-output-dir* — СПДС печатает листы и кладёт
;;;        склейку в <папка>\SPDS_<штамп>; перенос (move) больше не
;;;        нужен, блок удалён. База (если загружена) получает ту же
;;;        папку (AppData/PlotFrame/OutDir). Диалог: две РАМОЧКИ
;;;        качества — «Рамочка в PDF» и «Формат СПДС в PDF»; подписи
;;;        Низкое/Среднее/Высокое (пробелы в «авто -1», «авто +1»);
;;;        ПСПКАЧ: Высокое вместо Отличного.
;;; v0.59: подписи радиостроки базы в ПСПНАСТРОЙКИ: Низкое (авто-1) /
;;;        Среднее (авто) / Отличное (авто+1) — схема изменена в базе
;;;        3.20: сдвиг формата от авто-выбора, множитель не трогается.
;;; v0.58: лестница качества полностью переписана (заменяет
;;;        дефектный коммит 7f5d110, в который исправление не попало):
;;;        0 = формат-в-формат через psp-format-idx (parse даёт ИМЯ,
;;;        запись даёт только format-idx/size-up — иначе consp "A4");
;;;        1 = один psp-spds-size-up; 2 = size-up -> имя записи ->
;;;        size-up (второй прыжок по имени: раньше на вход шла ЗАПИСЬ,
;;;        format-idx давал nil, срабатывал fallback (nth 3) = A1 —
;;;        отсюда A1 при «Отличном» в логе 0.56).
;;; v0.56: качество базового PlotFrameToPDF (ЭКСПДФ) — вторая
;;;        радиострока в ПСПНАСТРОЙКИ (rq0/rq1/rq2 = x1/x2/x4,
;;;        setcfg AppData/PlotFrame/Quality; при загруженной базе
;;;        применяется сразу). В базе 3.19: *pfp-quality* читается
;;;        на прогоне и задаёт *pfp-size-factor* (1/2/4).
;;; v0.55: ЗАДАЧА «КАЧЕСТВО ПЕЧАТИ»: *psp-quality* 0/1/2 —
;;;        Низкое=формат в формат, Среднее=+1 (как всегда), Отличное=+2.
;;;        Выбор: команда ПСПКАЧ / PSPQUAL и радиострока в диалоге
;;;        настроек; хранение setcfg AppData/PlotSPDS/Quality.
;;; v0.54: поля всё ещё приходили пустыми: в ряде версий AutoCAD
;;;        get_tile НЕ работает после закрытия диалога. Значения
;;;        читаются в callback кнопки «Применить» (psp-tiles-read)
;;;        ДО done_dialog; блок сохранения использует *psp-t-*.
;;; v0.53: «неверный тип аргумента: stringp nil», папка не сохранялась:
;;;        unload_dialog стоял ДО чтения get_tile (после выгрузки
;;;        get_tile возвращает nil). Порядок исправлен: значения
;;;        читаются до выгрузки; все get_tile обёрнуты в psp-s->str.
;;; v0.52: DCL-диалога: у тайла spacer нельзя переопределять width
;;;        (фиксированный размер) — «неверный атрибут. Символ: spacer»,
;;;        строка 9. Заменено на безатрибутный spacer.
;;; v0.51: ИСПРАВЛЕНА «синтаксическая ошибка» при загрузке: в хвосте
;;;        диалога настроек 0.50 закрывающая скобка встала так, что
;;;        (princ) попал в форму (if ...) четвёртым аргументом; баланс
;;;        скобок при этом не нарушался (поэтому статическая батарея
;;;        молчала), а загрузчик AutoCAD форму отвергал. В батарею
;;;        добавлен тест арности if (2-3 аргумента).
;;; v0.50: ОКНО НАСТРОЕК ПСПНАСТРОЙКИ / PSPSET (DCL генерируется во
;;;        временную папку; хранение — реестр setcfg, восстановление
;;;        при загрузке psp-load-cfg): папка сохранения PDF (gs
;;;        собирает в temp, альбом переносится cmd move, открытие —
;;;        уже из новой папки), порог автосборки N (раньше 3), таймер
;;;        открытия (раньше 5), имя PDF-принтера (раньше только
;;;        глобальная), «Открывать результат», «Удалять одиночные».
;;;        Гейт *psp-open-pdf* заменён на *psp-open-res*.
;;; v0.49: по пользователю: при отказе от склейки (2-3 листа)
;;;        одиночные листы ОТКРЫВАЮТСЯ (через ~5 с, фоновый cmd), то же
;;;        для единственного листа. С «тихим» принтером это безопасно:
;;;        вкладки больше не плодит принтер (0.47/0.48).
;;; v0.48: по пользователю: принтер по умолчанию — PlotSPDSToPDF.pc3
;;;        (его «тихая» копия DWG To PDF.pc3 без галочки «Показывать
;;;        результаты в программе просмотра»). Добавлена справка
;;;        ПСППОМОЩЬ / PSPHELP / PSPPOMOSH: команды, порядок листов,
;;;        автосборка, пошаговое создание копии принтера (папка —
;;;        getenv PrinterConfigDir, ПЛОТТЕРМАНАДЖЕР не обязателен).
;;;        Баннер загрузки печатает имя принтера.
;;; v0.47: разгадка «самооткрывающихся» листов: DWG To PDF.pc3 ->>
;;;        «Параметры PDF» -> «Показывать результаты в программе
;;;        просмотра» — принтер сам открывает каждый отпечатанный
;;;        лист. На лету галочку не переключить (бинарный pc3),
;;;        введена глобальная *psp-pc3* (по умолчанию "DWG To
;;;        PDF.pc3"): пользователь один раз делает «тихую» копию
;;;        принтера без галочки и задаёт её имя. Сохранение в команде
;;;        настроек (задача 4/7).
;;; v0.46: по просьбе пользователя одиночные листы НЕ открываются
;;;        ВООБЩЕ (0.45 открывал их при отказе от склейки и при одном
;;;        листе — пользователь подтвердил: открывать только склейку).
;;;        Нет склейки — просто открывается папка сборки.
;;; v0.45: схема пользователя: склеиваем «закрытыми», открываем
;;;        ТОЛЬКО склейку; одиночные листы сами не запускаем. Если
;;;        склейки нет — открываем одиночные: при ответе «Нет» (2-3
;;;        листа) и при единственном листе (задержка ~5 с в фоновом
;;;        cmd). Вторая волна удаления остаётся страховкой от вкладок
;;;        просмотрщика.
;;; v0.44: диагностика: с закрытым просмотрщиком del с маской чист,
;;;        с открытым — ошибки «файл занят» (PDF-XChange блокирует
;;;        открытые вкладки). Добавлена вторая волна: фоновый цикл
;;;        del каждые ~5 с в течение ~1 мин — листы удаляются, как
;;;        только просмотрщик закрывают.
;;; v0.43: журнал 0.42: альбом открылся, но одиночные листы остались —
;;;        цепочка из 18 отдельных del не доводилась (длинная команда).
;;;        Диагностика подтвердила: короткая команда с маской работает.
;;;        Удаление одной командой: del "dir\L*.pdf" (альбом SPDS_*
;;;        маску не попадает).
;;; v0.42: задача «автоудаление одиночных файлов»: при УСПЕШНОЙ
;;;        склейке одиночные листы (pdfs) удаляются тем же фоновым
;;;        cmd с той же задержкой ~5 с: ping -> del листов -> start
;;;        склейки. Если склейка не состоялась (отказ «Нет», ошибка,
;;;        нет GS) — листы не трогаются. psp-open-pdf принял второй
;;;        аргумент dels.
;;; v0.41: журнал 0.40 показал: просмотрщик ЗАПУСКАЛСЯ, но ловил
;;;        «процесс не может получить доступ к файлу» — gs создаёт
;;;        выходной PDF сразу, а закрывает последним; открытие по факту
;;;        появления файла было гонкой. Открытие отложено на ~5 с
;;;        (ping -n 6) внутри фонового cmd: gs к тому моменту завершён.
;;; v0.40: диагностика на машине пользователя: вручную из консоли
;;;        открывались ВСЕ механизмы (cmd start, explorer, rundll32),
;;;        но старт из работающего LISP — нет (DDE-ассоциация .pdf,
;;;        PDF-XChange; без прокачки сообщений запуск терялся).
;;;        Новый psp-open-pdf: основной запуск через explorer.exe
;;;        (своя очередь сообщений), запасные rundll32 и cmd start;
;;;        каждое звено пишет T/nil в консоль.
;;; v0.39: по согласованию: после успешной сборки PDF открывается
;;;        системным просмотрщиком (startapp cmd /c start, путь в
;;;        кавычках с пустым заголовком). Выключатель *psp-open-pdf*
;;;        (по умолчанию T); команда настроек появится позже.
;;; v0.38: лист «0» — титульный: идёт перед листом 1 (раньше «0»
;;;        приравнивался к «без номера» и попадал в конец). Номер —
;;;        настоящий, если строка непуста и состоит из цифр, точек
;;;        и запятых (psp-sheet-p); имя файла — L00. Безномерные
;;;        листы по-прежнему в конце.
;;; v0.37: по просьбе пользователя откатлено расширение окна печати
;;;        (*psp-margin* удалён): окно = bbox прокси-объекта, как раньше.
;;;        Автосборка в один PDF при >3 листах осталась.
;;; v0.36: по запросу пользователя: больше трёх листов — сборка в один
;;;        PDF выполняется автоматически (вопрос остался для 2-3).
;;;        Лист 15.1 обрезался: bbox прокси-объекта СПДС (297.00x409.16)
;;;        меньше видимого кадра; окно печати расширено на *psp-margin*
;;;        (2% большей стороны, настраивается) — «Вписать» компенсирует.
;;; v0.35: по запросу пользователя: дробные листы (15, 15.1, 15.2)
;;;        идут по порядку номеров. Ранее atoi("15.1")=15 — все имели
;;;        один ключ и сортировались по вертикали. Номер парсится как
;;;        вещественный (psp-sheet-num), имена файлов честные:
;;;        L15, L15.1, L15.2 (psp-sheet-name), в таблице без ".0"
;;;        (psp-num-str). Строка номера хранится в позиции 8 записи.
;;; v0.34: 18/18 ЛИСТОВ В РЕАЛЬНОМ АЛЬБОМЕ (A4->A3 и A3->A2, обе
;;;        ориентации, дубликаты L15_2/_3) — печать стабильна. Склейка
;;;        во ВТОРОМ чертеже упала «no function definition:
;;;        PSP-S->STR»: переписка find-gs в 0.32 (срез «от find-gs до
;;;        merge-pdfs») молча удалила определение psp-s->str; в первом
;;;        чертеже её спасала старая загрузка v0.26 в той же сессии.
;;;        Функция возвращена.
;;; v0.33: СКЛЕЙКА ЗАРАБОТАЛА (ПСПГС -> GS[1] -> «Собрано в один PDF»),
;;;        но файл был пуст (одна белая страница): в список склейки
;;;        собирались ГОЛЫЕ имена (L01.pdf), gs искал их в своём рабочем
;;;        каталоге и не находил. Теперь в склейку идут полные пути.
;;;        Строка GS[4] печатается только если сработала ветка 4.
;;; v0.32: лог 0.31 показал: сработала ветка «рядом с чертежом» и
;;;        отдала ВЫДУМАННЫЙ путь (после 0.31 пути доверяются без
;;;        проверки) — GS_DLL из реестра даже не читался. Приоритет
;;;        изменён: реестр ПЕРВЫМ (там фактический каталог установки),
;;;        выдуманные пути рядом с чертежом — последними; логи только
;;;        от реально отработавших веток.
;;; v0.31: лог 0.30 добил: «GS_DLL -> type=STR», затем stringp T —
;;;        open тоже подменён (возвращает T для существующего файла),
;;;        а (close T) вне catch-all поднимал ошибку. Проверки файлов
;;;        в поиске GS убраны ВООБЩЕ: путь доверяется, существование
;;;        подтвердит сама склейка (выходной PDF появился — путь верный;
;;;        нет — таймаут и подсказка ПСПГС).
;;; v0.30: в 0.29 поиск GS не запускался вовсе — vl-catch-all-apply
;;;        получил (list nil) как аргумент для функции без аргументов
;;;        («слишком много аргументов»); вызов исправлен на nil.
;;; v0.29: лог 0.28 добил: «GS_DLL -> type=STR» напечатан, а следующий
;;;        strcat упал — vl-filename-directory ТОЖЕ возвращает T (хуки
;;;        СПДС затрагивают и его). Модуль отвязан от vl-filename-*:
;;;        каталог/имя разбираются вручную (psp-file-dir/psp-file-base
;;;        на substr), существование файла — open/close (findfile
;;;        остался только индикатором). Поиск GS обёрнут в catch-all
;;;        с печатью ошибки; команда ПСПГС — ручной путь.
;;; v0.28: НАЙДЕНА ОКОНЧАТЕЛЬНАЯ ПРИЧИНА ВСЕХ «stringp T»: findfile
;;;        у пользователя возвращает T вместо пути существующего файла
;;;        (подозрение на вмешательство СПДС GraphiCS). Улики: «TT» в
;;;        тесте 0.19, gs=T в 0.26, падение сразу после «type=STR» на
;;;        strcat с результатом поиска. try теперь возвращает
;;;        собственный путь, а не результат findfile. Добавлена команда
;;;        ПСПГС / PSPGS: задать путь к Ghostscript вручную и запомнить
;;;        (setcfg, восстанавливается при загрузке).
;;; v0.27: склейка показала gs=T — psp-find-gs вернул T вместо пути
;;;        (старый тест пользователя (princ (psp-find-gs)) -> «TT»,
;;;        тот же случай). Поиск инструментирован: каждый этап печатает
;;;        результат; в реестре читаются GS_DLL и GS_LIB (10.x);
;;;        наружу проходит только строка, не-строка -> nil.
;;; v0.26: печать 4/4 прошла, но склейка упала «stringp T» — источник
;;;        статически не найден. Склейка сделана пуленепробиваемой:
;;;        все части команды через psp-s->str (не-строка НЕ роняет
;;;        strcat, а видна в печатаемой команде), вызов под
;;;        vl-catch-all с печатью ошибки, gs и целевой путь печатаются
;;;        до склейки — следующий лог покажет всё.
;;; v0.25: ТРАНСКРИПТ 0.24 РАСКРЫЛ ПРИЧИНУ: подсказке «Введите имя
;;;        файла» уходил ответ «_As» — в общей ленте был ЛИШНИЙ ответ
;;;        «_N» («не масштабировать веса»): в этой сборке AutoCAD такого
;;;        вопроса нет, и лента сбита на один токен с этого места.
;;;        Лишний ответ убран; на случай других сборок — переключатель
;;;        ПСПЛЕНТА / PSPTAPE (добавить «_N» обратно). Предустановка
;;;        листа подтверждена транскриптом (формат применен).
;;; v0.24: гипотеза о вкладке Листа не подтвердилась (пользователь
;;;        запускал из модели) — принудительный TILEMODE откатан (к тому
;;;        же setvar «TILEMODE» капризничает после снятия зависшей
;;;        печати). Новое: после предустановки формат читается обратно —
;;;        в консоли видно, применился ли он («предустановка: <имя>» /
;;;        «НЕ ПРИМЕНИЛАСЬ»); молчаливый отказ предустановки — главный
;;;        подозреваемый в паре вопросов «Сохранить изменения...».
;;; v0.23: РАЗГАДКА «ЗАСТРЯВАНИЙ»: хвост «Сохранить изменения параметров
;;;        листа?/Перейти к печати?» — вопросы ветки ЛИСТА; при запуске с
;;;        вкладки листа лента шла по неверной ветке. На время экспорта
;;;        принудительно TILEMODE=1 (рамки СПДС лежат в модели), вкладка
;;;        восстанавливается после печати. Из ветки листа удалён фантомный
;;;        ответ «не печатать лист последним». Эхо печати: отдельные
;;;        команды ПСПЭХОВКЛ / ПСПЭХОВЫКЛ (PSPECHOON / PSPECHOOFF).
;;;        Двойной учёт пропусков устранён.
;;; v0.22: прогоны без «Печатная область чертежа: ...» = -ПЕЧАТЬ
;;;        спотыкается ДО шага окна; вопрос скрыт CMDECHO=0. Новый
;;;        диагностический режим ПСПЭХО / PSPECHO: не глушит эхо —
;;;        в консоли виден весь транскрипт вопросов и ответов.
;;;        Пропуск не учитывается дважды (было 8 вместо 4).
;;; v0.21: ответ «Д» (Да) не распознавался: getkword с двуязычным
;;;        initget вернул не форму «Да», а иную форму ключа. Сравнение
;;;        заменено на список принимаемых: Да/Yes без учета регистра.
;;; v0.20: автоискатель Ghostscript смотрит и в gs\\bin\\ рядом с
;;;        чертежом (стандартная раскладка установки/архива).
;;; v0.19: СБОРКА В ОДИН МНОГОСТРАНИЧНЫЙ PDF. Если напечатано больше
;;;        одного листа и найден Ghostscript (*psp-gs* -> gs рядом с
;;;        чертежом -> реестр -> Program Files), предлагается «Собрать
;;;        все листы в один PDF? [Да/Нет] <Да>»: L01...LNN склеиваются
;;;        в SPDS_<дата>_<время>.pdf рядом с подпапкой. Без GS —
;;;        подсказка, постраничные PDF остаются.
;;; v0.18: прогон 0.17: пара «Сохранить изменения параметров листа?»/
;;;        «Перейти к печати?» вклинилась в ленту (в прогоне 4/4 была
;;;        подавлена PAPERUPDATE=0) — лента сдвинулась, все листы ушли
;;;        в «_As». Добавлены: печать фактических PAPERUPDATE/
;;;        BACKGROUNDPLOT перед циклом (видно, принялся ли 0); после
;;;        каждой печати проверка CMDACTIVE — застрявший вопрос
;;;        снимается по ESC (psp-clear-stuck), лист помечается
;;;        пропущенным, каскад сдвига невозможен.
;;; v0.17: по выбору пользователя имена файлов: L01.pdf, L02.pdf...
;;;        (префикс L + номер листа; дубликаты номера: L01_2, L01_3).
;;; v0.16: прогон 4/4 без вопросов (PAPERUPDATE=0 подтвердился в свежем
;;;        чертеже, порядок по листам верный, обе ориентации, упрощённая
;;;        рамка с 22 полями тоже прошла). Отладочные контрольные точки
;;;        [1]-[6] удалены; структура с разнесёнными setq сохранена.
;;; v0.15: первый прогон ЭКССПДСПДФ прошёл, но свежий чертёж задавал
;;;        два вопроса («Сохранить изменения параметров листа?»,
;;;        «Перейти к печати?») — пара PAPERUPDATE; лента сдвигалась и
;;;        файл уходил с посторонним именем. На время экспорта
;;;        PAPERUPDATE=0 (подавить), после — восстановление. Если PDF не
;;;        найден после печати, печатается ожидаемый путь.
;;; v0.14: ПРИЧИНА «stringp T» НАЙДЕНА И ИСПРАВЛЕНА: булевы поля СПДС
;;;        (группа 290) entget отдаёт как T/nil; разбор оставлял такое
;;;        значение как есть, и (atoi T) падал. Разбор 300/40/90/290 теперь
;;;        понимает T->"1", nil->"0" и всё прочее через vl-princ-to-string;
;;;        кратность в экспорте читается со страховкой типа.
;;; v0.13: трассировка локализовала сбой: между «выбрано объектов» и
;;;        сортировкой (цикл сбора). Добавлены контрольные точки [1]-[6]
;;;        по шагам цикла: ssname -> vla-объект -> поля entget -> формат/
;;;        лист -> габариты -> сбор позиции. Последняя напечатанная точка
;;;        укажет оператор, вызывающий «stringp T».
;;; v0.12: по логу первого прогона ЭКССПДСПДФ: необнаруженная ошибка
;;;        «неверный тип аргумента: stringp T» — добавлена поэтапная
;;;        трассировка печати (объектов/сортировка/папка/каждый лист),
;;;        psp-page-preset обёрнут в vl-catch-all-apply, psp-output-dir
;;;        переживает пустой TEMP. Ошибка диага (тройки вместо строк)
;;;        исправлена в PlotSPDSDiag 0.12.
;;; v0.11: СВОЙСТВА СПДС НАЙДЕНЫ: в entget объекта парами (301 "ключ")
;;;        (300 "значение"): Format, Sheet, SheetCount, Designation,
;;;        Orientation, Multiplicity (журнал 0.10). Новый psp-spds-fields;
;;;        формат/лист/листов в ЭКССПДСПДФ и диагностике читаются из
;;;        entget (COM-свойства остались запасным каналом). Экстрактор
;;;        собирает пары 301/300 (строки вида "Format: A4"). Кратность
;;;        Multiplicity>1 даёт бумагу на N-1 шагов вверх (как "ФорматXN").
;;; v0.9: ПРИЧИНА СБОЕВ ЗАГРУЗКИ НАЙДЕНА. (load) в AutoCAD не читает
;;;        .lsp дальше ~36 Кбайт (36864 = 0x9000): v0.1-v0.4 (до 36433
;;;        байт) грузились, все версии с v0.5 (45317+) падали с «синтак-
;;;        сической ошибкой» на форме, содержащей этот байт. Диагностика
;;;        вынесена в PlotSPDSDiag.lsp; оба файла теперь меньше предела.
;;;
;;; Этапы разработки:
;;;   0. Диагностика — ЭКССПДСДИАГ: типы объектов, свойства, дамп.
;;;   1. Серийная печать — ЭКССПДСПДФ: сортировка по «листу»,
;;;      бумага на шаг вверх (A4->A3, A3->A2 ...), файлы s01.pdf ...
;;;   2. Сборка в один многостраничный PDF — следующий этап.

(vl-load-com)

(setq *psp-ver* "0.85")

(setq *psp-open-mode* "rundll")
(setq *psp-open-delay* 300)
(setq *psp-unit-scale* 1.0)
(setq *psp-subdir* "PlotFramePDF")
(setq *psp-color-mode* nil)
(setq *psp-ctb-mono* "monochrome.ctb")
(setq *psp-ctb-color* "acad.ctb")
(setq *psp-output-dir* nil)
;; Путь к Ghostscript (gswin64c.exe); nil — искать автоматически.
;; Команда ПСПГС задаёт путь вручную и запоминает его (setcfg).
(setq *psp-gs* (getcfg "AppData/PlotSPDS/GS"))
(if (= *psp-gs* "") (setq *psp-gs* nil))

;; Имя примитива СПДС и каналы чтения свойств (порядок = приоритет)
(setq *psp-spds-entity* "SPDSFORMAT")

;; Разделы помечены маркерами загрузки (ПСП: секция N/10)
(setq *psp-spds-props-format*
      '("Format" "Формат" "SheetFormat" "FrameFormat" "FormatName"))
(setq *psp-spds-props-sheet*
      '("Sheet" "Лист" "SheetNo" "SheetNumber" "Номер"))
(setq *psp-spds-props-total*
      '("Sheets" "Листов" "SheetsTotal" "TotalSheets"))

;; Таблица форматов (как в PlotFrameToPDF + строка A4)
;; (короткое W_L H_L "портрет" "альбом")
(setq *psp-formats*
  '(("A4"  297  210
     "ISO_full_bleed_A4_(210.00_x_297.00_MM)"
     "ISO_full_bleed_A4_(297.00_x_210.00_MM)")
    ("A3"  420  297
     "ISO_full_bleed_A3_(297.00_x_420.00_MM)"
     "ISO_full_bleed_A3_(420.00_x_297.00_MM)")
    ("A2"  594  420
     "ISO_full_bleed_A2_(420.00_x_594.00_MM)"
     "ISO_full_bleed_A2_(594.00_x_420.00_MM)")
    ("A1"  841  594
     "ISO_full_bleed_A1_(594.00_x_841.00_MM)"
     "ISO_full_bleed_A1_(841.00_x_594.00_MM)")
    ("A0"  1189 841
     "ISO_full_bleed_A0_(841.00_x_1189.00_MM)"
     "ISO_full_bleed_A0_(1189.00_x_841.00_MM)")
    ("2A0" 1682 1189
     "ISO_full_bleed_2A0_(1189.00_x_1682.00_MM)"
     "ISO_full_bleed_2A0_(1682.00_x_1189.00_MM)")
    ("4A0" 2378 1682
     "ISO_full_bleed_4A0_(1682.00_x_2378.00_MM)"
     "ISO_full_bleed_4A0_(2378.00_x_1682.00_MM)")))

;; Сохранённые устройство/формат активного листа (на время печати)
(setq *psp-page-saved* nil)
;; Метка этапа — попадает в сообщение об ошибке
(setq *psp-stage* "-")
;; T: не глушить CMDECHO при печати — видно все подсказки -ПЕЧАТЬ
;; (переключается командой ПСПЭХО / PSPECHO)
(setq *psp-plot-echo* nil)
;; T: в ленту -ПЕЧАТЬ добавляется ответ «_N» для вопроса
;; «Масштабировать веса линий?» (переменная *psp-tape-mode*)
(setq *psp-tape-mode* nil)
;; Настройки (окно — команда ПСПНАСТРОЙКИ / PSPSET; хранение setcfg)
(setq *psp-pdf-dir* "")      ; папка сохранения PDF ("" = temp)
(setq *psp-auto-merge-n* 3)  ; автосборка при листах БОЛЬШЕ этого числа
(setq *psp-open-delay-s* 5)  ; задержка открытия результата, секунд
(setq *psp-open-res* T)      ; открывать результат (склейку/одиночные)
(setq *psp-del-singles* T)   ; удалять одиночные листы после склейки
;; Качество печати: 0 = формат в формат, 1 = +1 формат (как всегда),
;; 2 = +2 формата. Выбор — строка в ПСПНАСТРОЙКИ
(setq *psp-quality* 1)
;; Имя PDF-принтера. В DWG To PDF.pc3 может быть включено «Показывать
;; результаты в программе просмотра» — тогда AutoCAD САМ открывает
;; каждый отпечатанный лист (вкладки просмотрщика, блокировка
;; удаления). Один раз сделайте «тихую» копию принтера без этой
;; галочки (как — команда ПСППОМОЩЬ) и укажите её имя здесь или
;; (setq *psp-pc3* "Имя.pc3") ПОСЛЕ загрузки модуля.
(setq *psp-pc3* "PlotSPDSToPDF.pc3")

;; Восстановление настроек из реестра (записывает ПСПНАСТРОЙКИ)
(defun psp-load-cfg ( / s n)
  (setq s (getcfg "AppData/PlotSPDS/PDFDir"))
  (if (and (= (type s) 'STR) (/= s ""))
    (setq *psp-pdf-dir* s *psp-output-dir* s))
  ;; Параметры печати (задача 12): подхват в ОБА модуля
  ;; (СПДС печатает по *psp-*, база — по *pfp-*)
  (setq s (getcfg "AppData/PlotFrame/ColorMode"))
  (if (= (type s) 'STR)
    (setq *pfp-color-mode* (= s "1") *psp-color-mode* (= s "1")))
  (setq s (getcfg "AppData/PlotFrame/CtbMono"))
  (if (and (= (type s) 'STR) (/= s ""))
    (setq *pfp-ctb-mono* s *psp-ctb-mono* s))
  (setq s (getcfg "AppData/PlotFrame/CtbColor"))
  (if (and (= (type s) 'STR) (/= s ""))
    (setq *pfp-ctb-color* s *psp-ctb-color* s))
  (setq s nil n (getcfg "AppData/PlotSPDS/AutoMergeN"))
  (if (= (type n) 'STR) (setq s (atoi n)))
  (if (and (numberp s) (> s 0)) (setq *psp-auto-merge-n* s))
  (setq s nil n (getcfg "AppData/PlotSPDS/OpenDelay"))
  (if (= (type n) 'STR) (setq s (atoi n)))
  (if (and (numberp s) (>= s 0)) (setq *psp-open-delay-s* s))
  (setq s (getcfg "AppData/PlotSPDS/OpenRes"))
  (cond ((= s "1") (setq *psp-open-res* T))
        ((= s "0") (setq *psp-open-res* nil)))
  (setq s (getcfg "AppData/PlotSPDS/DelSingles"))
  (cond ((= s "1") (setq *psp-del-singles* T))
        ((= s "0") (setq *psp-del-singles* nil)))
  (setq s (getcfg "AppData/PlotSPDS/PC3"))
  (if (and (= (type s) 'STR) (/= s "")
           (wcmatch (strcase s T) "*`.pc3"))
    (setq *psp-pc3* s))
  (setq s nil n (getcfg "AppData/PlotSPDS/Quality"))
  (if (= (type n) 'STR) (setq s (atoi n)))
  (if (and (numberp s) (>= s 0) (<= s 2)) (setq *psp-quality* s))
  (princ))
(psp-load-cfg)

;; ---------------------------------------------------------------------------
;; Утилиты

;; ---------------------------------------------------------------------------

(defun psp-get (obj prop)
  (vl-catch-all-apply 'vlax-get-property (list obj prop)))

(defun psp-safe-put (obj prop val)
  (not (vl-catch-all-error-p
         (vl-catch-all-apply 'vlax-put-property (list obj prop val)))))

;; variant -> значение; safearray/прочее -> как есть; nil при ошибке.
(defun psp-va->list-unwrap (x / v)
  (cond
    ((null x) nil)
    ((= (type x) 'VARIANT)
     (setq v (vl-catch-all-apply 'vlax-variant-value (list x)))
     (if (vl-catch-all-error-p v) nil v))
    (t x)))

(defun psp-pad-right (s width / n)
  (setq n (- width (strlen s)))
  (while (> n 0) (setq s (strcat s " ") n (1- n))) s)

(defun psp-default-dir ()
  (strcat (getenv "TEMP") "\\" *psp-subdir*))

(defun psp-output-dir ( / d)
  (if (null *psp-output-dir*)
    (progn
      (setq d (getenv "TEMP"))
      (if (null d) (setq d (getvar "TEMP")))
      (if (null d) (setq d "C:"))
      (setq d (strcat d "\\" *psp-subdir*))
      (vl-mkdir d)
      (setq *psp-output-dir* d)))
  *psp-output-dir*)

(defun psp-clear-stuck ( / doc i)
  (setq doc (vl-catch-all-apply 'vla-get-ActiveDocument
                                (list (vlax-get-acad-object))))
  (setq i 0)
  (while (and (< i 5) (> (getvar "CMDACTIVE") 0))
    (vl-catch-all-apply 'vla-SendCommand (list doc (chr 27)))
    (setq i (1+ i)))
  (princ))

(defun psp-sleep (ms / old-cmdecho)
  (setq old-cmdecho (getvar "CMDECHO"))
  (setvar "CMDECHO" 0)
  (command "_.delay" ms)
  (setvar "CMDECHO" old-cmdecho))

(defun psp-open-rundll (path / args)
  (setq args (strcat "url.dll,FileProtocolHandler \"" path "\""))
  (startapp "rundll32.exe" args))

(defun psp-open (path)
  (if (= *psp-open-mode* "rundll")
    (psp-open-rundll path)
    (startapp "explorer.exe" path)))

;; Предустановка устройства и формата активного листа через ActiveX:

;; -ПЕЧАТЬ не вставляет лишний вопрос о неподдерживаемом формате.
;; Прежние значения -> *psp-page-saved* -> psp-page-restore.


;; Предустановка бумаги активному листу. v1.11: имя ставится ТОЛЬКО
;; если оно есть в списке бумаг устройства; при отсутствии точного
;; имени берётся та же формат-группы (префикс до «_(») в ЛЮБОЙ ори-
;; ентации, а несовпадение ориентации компенсируется разворотом
;; чертежа в ленте (*psp-rot-adj* — слот «Перевернуть?» = Да). При-
;; чина: подстановка отвергнутых имёнAutoCAD resolving'ит хаотично
;; (то A2, то ANSI_A, то A0) — надёжны только имена из списка.
;; Прежние устройство/бумага сохраняются в *psp-page-saved*.
;; Возвращает фактическое имя бумаги или nil.
;; Предустановка бумаги активному листу. v1.12: ПОРЯДОК ИСПРАВЛЕН —
;; сначала переключаем лист на целевое устройство (*psp-pc3*), ЗАТЕМ
;; берём его список бумаг (в v1.11/v1.10 список брали у СТАРОГО ус-
;; тройства — например FinePrint, где нет ISO_* имён: want=nil ->
;; бумага не ставилась -> печать на дефолте устройства ANSI_A).
;; Имя ставится ТОЛЬКО из списка: точное, иначе та же формат-груп-
;; па (префикс до «_(»); нехватка альбомной ориентации (2A0/A0 у
;; pc3 только книжные) компенсируется разворотом чертежа в ленте
;; (*psp-rot-adj* -> «Перевернуть?» = Да). Прежние устройство/бу-
;; мага сохраняются в *psp-page-saved* (восстановление — psp-page-
;; -restore). Возвращает фактическое имя бумаги или nil.
;; Предустановка бумаги активному листу. v1.13: префикс формат-
;; группы считается БЕЗ потери символа (vl-string-search даёт
;; 0-based смещение «_(», префикс = substr 1 k; было (1- k) —
;; «2A0» обрезалось до «2A», сопоставление не работало никогда).
;; Понятие «разворота» УДАЛЕНО: «Перевернуть чертёж?» в -ПЕЧАТЬ —
;; поворот на 180°, а не смена ориентации; книжную бумагу (2A0/A0
;; у pc3 есть только книжными) разворачивает САМ слот ориентации
;; (_L/_P), который шлётся по рамке. Имя ставится только из списка
;; бумаг устройства: точное или та же формат-группа. Прежние уст-
;; ройство/бумага сохраняются в *psp-page-saved*. Возвращает факт.
(defun psp-page-preset (media-name / doc layout cfg med names lst want k n x)
  (setq *psp-page-saved* nil)
  (setq doc (psp-get (vlax-get-acad-object) 'ActiveDocument))
  (setq layout (psp-get doc 'ActiveLayout))
  (if (or (null layout) (vl-catch-all-error-p layout))
    nil
    (progn
      (setq cfg (psp-get layout 'ConfigName)
            med (psp-get layout 'CanonicalMediaName))
      (setq *psp-page-saved*
            (list (if (vl-catch-all-error-p cfg) nil cfg)
                  (if (vl-catch-all-error-p med) nil med)))
      ;; устройство — ПЕРВЫМ (после этого валиден список его бумаг)
      (psp-safe-put layout 'ConfigName *psp-pc3*)
      (setq names (vl-catch-all-apply
                    '(lambda ( )
                       (vlax-invoke layout
                                    'GetCanonicalMediaNames))))
      (setq lst (if (and (not (vl-catch-all-error-p names))
                         (= (type names) 'LIST))
                  names nil))
      (setq want nil)
      (if lst
        (progn
          ;; точное имя, если есть в списке
          (foreach x lst
            (if (and (null want) (= (type x) 'STR)
                     (= (strcase x) (strcase media-name)))
              (setq want x)))
          ;; иначе та же формат-группа в любой ориентации
          (if (null want)
            (progn
              (setq k (vl-string-search "_(" media-name)
                    n (if (> k 0) (substr media-name 1 k) media-name))
              (foreach x lst
                (if (and (null want) (= (type x) 'STR)
                         (wcmatch (strcase x)
                                  (strcat (strcase n) "_(*")))
                  (setq want x))))))
        ;; списка нет — шлём запрошенное, как в 3.2x
        (setq want media-name))
      ;; бумага — только подтверждённая списком
      (if want
        (psp-safe-put layout 'CanonicalMediaName want))
      (setq med (psp-get layout 'CanonicalMediaName))
      (if (vl-catch-all-error-p med) nil med))))




(defun psp-page-restore ( / doc layout)
  (if *psp-page-saved*
    (progn
      (setq doc (psp-get (vlax-get-acad-object) 'ActiveDocument))
      (setq layout (psp-get doc 'ActiveLayout))
      (if (and (not (null layout)) (not (vl-catch-all-error-p layout)))
        (progn
          (if (car *psp-page-saved*)
            (psp-safe-put layout 'ConfigName (car *psp-page-saved*)))
          (if (cadr *psp-page-saved*)
            (psp-safe-put layout 'CanonicalMediaName
                          (cadr *psp-page-saved*)))))
      (setq *psp-page-saved* nil)))
  (princ))

;; ---------------------------------------------------------------------------
;; Печать окна через -ПЕЧАТЬ (общая лента ответов, Модель/Лист)

;; ---------------------------------------------------------------------------

;; Наборы вопросов -ПЕЧАТЬ у Модели и Листа различаются: у Модели нет
;; вопросов «лист последним»/«удалять скрытые», но есть «Задать
;; тонирование» (ответ — ключевое слово). Лента собирается по TILEMODE.
(defun psp-plot-tape (fname media-name rot-str ctb x1 y1 x2 y2
                      media-chk alt / tape old-cmdecho)
  (setq old-cmdecho (getvar "CMDECHO"))
  (setvar "CMDECHO" (if *psp-plot-echo* 1 0))
  (setq tape
    (append
      (list "_.-plot"
            "_Y"                     ; подробная настройка
            ""                       ; текущий лист
            *psp-pc3*                ; устройство
            (cond                     ; nil в ленте command недопустим!
              ((= 1 (getvar "TILEMODE")) "") ;Лист: Enter — формат уже
                                       ;предустановлен; лист хранит ПОРТ-
                                       ;РЕТНЫЙ канон, шлём Enter, а не план
              ((= (type media-chk) 'STR) media-chk) ;Модель: факт преду-
                                       ;становки (обычно совпадает с планом)
              (t media-name))
            "_M"                     ; мм
            rot-str                  ; ориентация _L / _P (разворачивает
            "_N"                     ; печать и на книжной бумаге)
            "_W"                     ; область: Рамка
            (list x1 y1)             ; нижний левый угол
            (list x2 y2)             ; верхний правый угол
            "_F"                     ; вписать
            "_C"                     ; центрировать
            "_Y"                     ; учитывать стили печати
            ctb                      ; CTB-файл
            "_Y")                    ; учитывать веса линий
      ;; В части сборок AutoCAD есть вопрос «Масштабировать веса линий?»,
      ;; в части (см. транскрипт 0.24) его нет. По умолчанию НЕТ (лишний
      ;; ответ сдвигал ленту: имя файла получало "_As"). Переключение:
      ;; (переменная *psp-tape-mode*).
      (if (= 1 (getvar "TILEMODE"))
        ;; --- вкладка Модель ---
        (append
          (if *psp-tape-mode*        ; «Масштабировать веса?» задаёт не
            (list "_N"))             ; каждая сборка
          (list
            "_As"                    ; тонирование: по отображению
            fname                    ; имя файла
            "_N"                     ; не сохранять в параметры
            "_Y"))                   ; печатать
        ;; --- вкладка Лист ---
        ;; Три «Нет» (масштабировать веса / печатать лист первым /
        ;; скрывать объекты листа). Вопрос «записать изменения в
        ;; макет» появляется ТОЛЬКО когда настройки печати отлича-
        ;; ются от сохранённых в листе, поэтому постоянного ответа
        ;; под него нет: второй заход (alt) шлёт четвёртое «Нет».
        (append
          (list "_N" "_N" "_N")
          (if alt (list "_N"))
          (list fname "_N" "_Y")))))
  (apply 'command tape)
  (setvar "CMDECHO" old-cmdecho)
  t)

;; ---------------------------------------------------------------------------
;; СПДС: чтение свойств и геометрии

;; ---------------------------------------------------------------------------

;; Чтение свойства по списку имён-кандидатов.
;; Возвращает (значение имя_канала) или nil. Значение -> строка.
(defun psp-spds-prop-ex (obj names / nm avail v val)
  (setq val nil)
  (while (and names (null val))
    (setq nm (car names)
          avail (vl-catch-all-apply 'vlax-property-available-p
                                    (list obj nm T)))
    (if (and (not (vl-catch-all-error-p avail)) avail)
      (progn
        (setq v (psp-get obj nm))
        (if (not (vl-catch-all-error-p v))
          (progn
            (setq val (psp-va->list-unwrap v))
            (if (not (null val))
              (setq val (cond
                          ((= (type val) 'STR) (if (= val "") nil val))
                          ((= (type val) 'INT) (itoa val))
                          ((= (type val) 'REAL) (itoa (fix val)))
                          (t (vl-princ-to-string val)))))))))
    (if (null val) (setq names (cdr names))))
  (if val (list val nm) nil))

(defun psp-spds-prop (obj names / r)
  (setq r (psp-spds-prop-ex obj names))
  (if r (car r) nil))

;; Значение hex-символа (0-9, A-F, a-f) или nil.
(defun psp-hexval (ch / c)
  (setq c (ascii ch))
  (cond
    ((and (>= c 48) (<= c 57)) (- c 48))
    ((and (>= c 65) (<= c 70)) (- c 55))
    ((and (>= c 97) (<= c 102)) (- c 87))
    (t nil)))

;; Строка hex-пар -> байтовая строка. Некорректные хвосты игнорируются.
(defun psp-hex->str (hex / i h1 h2 res)
  (setq i 1 res "")
  (if hex
    (progn
      (while (<= (+ i 1) (strlen hex))
        (setq h1 (psp-hexval (substr hex i 1))
              h2 (psp-hexval (substr hex (1+ i) 1)))
        (if (and h1 h2)
          (setq res (strcat res (chr (+ (* 16 h1) h2)))))
        (setq i (+ i 2)))))
  res)

;; Читаемые фрагменты (печатаемые коды 32..255) длиной >= minlen.
(defun psp-printable-runs (s minlen / i code run res)
  (setq i 1 run "" res nil)
  (if s
    (progn
      (while (<= i (strlen s))
        (setq code (ascii (substr s i 1)))
        (if (and (>= code 32) (/= code 127) (<= code 255))
          (setq run (strcat run (substr s i 1)))
          (progn
            (if (>= (strlen run) minlen) (setq res (cons run res)))
            (setq run "")))
        (setq i (1+ i)))
      (if (>= (strlen run) minlen) (setq res (cons run res)))))
  (reverse res))

;; Объединение строк через разделитель.
(defun psp-join (sep lst / res)
  (setq res "")
  (foreach s lst
    (setq res (if (= res "") s (strcat res sep s))))
  res)

;; Строки объекта СПДС: entget (группы 1, 3 и бинарные 310-312),
;; XRecord'ы расширения словаря, XData. Каждый шаг защищён.
(defun psp-spds-strings (obj ent / ed item runs s res dict it nm k301
                             codes vals cl vl i v)
  (setq res nil)
  ;; 1) entget: тексты, бинарные данные, XData (группы 1000+;
  ;;    entget с '("*") возвращает XData всех приложений)
  (setq ed (vl-catch-all-apply 'entget (list ent '("*"))))
  (if (and (not (vl-catch-all-error-p ed)) ed)
    (foreach item ed
      (cond
        ((and (= (car item) 301) (= (type (cdr item)) 'STR))
         (setq k301 (cdr item)))
        ((and k301 (member (car item) '(300 40 90 290)))
         (setq v (cdr item)
               v (cond ((= (type v) 'STR) v)
                       ((= (type v) 'INT) (itoa v))
                       ((= (type v) 'REAL) (rtos v 2 2))
                       ((eq v T) "1")
                       ((null v) "0")
                       (t (vl-princ-to-string v))))
         (setq res (cons (strcat k301 ": " v) res)
               k301 nil))
        ((and (member (car item) '(1 3))
              (= (type (cdr item)) 'STR)
              (> (strlen (cdr item)) 1))
         (setq res (cons (cdr item) res)))
        ((and (member (car item) '(310 311 312))
              (= (type (cdr item)) 'STR))
         (setq runs (psp-printable-runs (psp-hex->str (cdr item)) 4))
         (foreach s runs (setq res (cons s res))))
        ((and (= (car item) 1000) (= (type (cdr item)) 'STR)
              (> (strlen (cdr item)) 1))
         (setq res (cons (cdr item) res)))
        ((and (= (car item) 1004) (= (type (cdr item)) 'STR))
         (setq runs (psp-printable-runs (psp-hex->str (cdr item)) 4))
         (foreach s runs (setq res (cons s res))))
        ((and (>= (car item) 1010) (<= (car item) 1071))
         (setq res (cons (strcat "XD[" (itoa (car item)) "]="
                                 (vl-princ-to-string (cdr item)))
                         res))))))
  ;; 2) расширение словаря: XRecord'ы
  (setq dict (vl-catch-all-apply 'vla-getextensiondictionary
                                 (list obj)))
  (if (and (not (vl-catch-all-error-p dict)) dict)
    (vlax-for it dict
      (setq nm (psp-get it 'ObjectName))
      (if (and (not (vl-catch-all-error-p nm)) (= nm "AcDbXrecord"))
        (progn
          (setq codes nil vals nil)
          (vl-catch-all-apply 'vla-getxrecorddata (list it 'codes 'vals))
          (if (and codes (not (vl-catch-all-error-p codes)))
            (progn
              (setq codes (vl-catch-all-apply 'vlax-safearray->list
                              (list (psp-va->list-unwrap codes))))
              (if (vl-catch-all-error-p codes) (setq codes nil))))
          (if (and vals (not (vl-catch-all-error-p vals)))
            (progn
              (setq vals (vl-catch-all-apply 'vlax-safearray->list
                              (list (psp-va->list-unwrap vals))))
              (if (vl-catch-all-error-p vals) (setq vals nil))))
          (if (and codes vals)
            (progn
              (setq i 0)
              (while (and (< i (length codes))
                          (< i (length vals)))
                (setq v (psp-va->list-unwrap (nth i vals)))
                (if (= (type v) 'SAFEARRAY)
                  (setq v (vl-catch-all-apply 'vlax-safearray->list
                              (list v))))
                (if (vl-catch-all-error-p v) (setq v nil))
                (if (and v (= (type v) 'LIST))
                  (setq v (psp-join " " (mapcar 'vl-princ-to-string v))))
                (if v
                  (setq res (cons (strcat "XR[" (itoa (nth i codes))
                                          "]=" (vl-princ-to-string v))
                                  res)))
                (setq i (1+ i)))))))))
  (reverse res))

;; Замена кириллических гомоглифов на латиницу (остальные символы
;; не трогаются — позиции сохраняются).
(defun psp-spds-latinize (s / i ch res)
  (setq i 1 res "")
  (while (<= i (strlen s))
    (setq ch (substr s i 1)
          res (strcat res
                (cond
                  ((member ch '("А" "A")) "A")
                  ((member ch '("В" "B")) "B")
                  ((member ch '("С" "C")) "C")
                  ((member ch '("Е" "E")) "E")
                  ((member ch '("Н" "H")) "H")
                  ((member ch '("К" "K")) "K")
                  ((member ch '("М" "M")) "M")
                  ((member ch '("О" "O")) "O")
                  ((member ch '("Р" "P")) "P")
                  ((member ch '("Т" "T")) "T")
                  ((member ch '("У" "Y")) "Y")
                  ((member ch '("Х" "X")) "X")
                  (t ch)))
          i (1+ i)))
  res)

;; Кандидаты формата в строках: A1..A5 (латиница/кириллица),
;; 2A0/4A0; кратность вида A4X2/A4Х2 тоже отмечается.
(defun psp-spds-candidates (strs / res s su i ch n1 n2 tok)
  (foreach s strs
    (setq su (psp-spds-latinize (strcase s)) i 1)
    (while (<= i (strlen su))
      (setq ch (substr su i 1))
      (cond
        ;; 2A0 / 4A0
        ((and (member ch '("2" "4"))
              (<= (+ i 2) (strlen su))
              (member (substr su (1+ i) 1) '("A"))
              (= (substr su (+ i 2) 1) "0"))
         (setq tok (strcat ch "A0"))
         (if (not (member tok res)) (setq res (cons tok res)))
         (setq i (+ i 2)))
        ;; A0..A5 (в т.ч. с кратностью A4X3)
        ((member ch '("A"))
         (setq n1 (if (<= (1+ i) (strlen su))
                    (substr su (1+ i) 1) ""))
         (if (and (>= (ascii n1) 48) (<= (ascii n1) 53))
           (progn
             (setq tok (strcat ch n1)
                   n2 (if (<= (+ i 2) (strlen su))
                        (substr su (+ i 2) 1) ""))
             (if (and (member n2 '("X"))
                      (<= (+ i 3) (strlen su))
                      (>= (ascii (substr su (+ i 3) 1)) 49)
                      (<= (ascii (substr su (+ i 3) 1)) 57))
               (setq tok (strcat tok "X" (substr su (+ i 3) 1))))
             (if (not (member tok res)) (setq res (cons tok res))))))
        (t nil))
      (setq i (1+ i))))
  (reverse res))

;; Свойства строки диагностики: (формат-имя лист листов габариты).
;; Пары (301 "ключ") (300 "значение") в entget SPDSFORMAT: Format, Sheet,
;; SheetCount, Designation, Orientation, Multiplicity, Name, Info и т.д.
(defun psp-spds-fields (ent / ed item key val res)
  (setq ed (entget ent) res nil key nil)
  (foreach item ed
    (cond
      ((and (= (car item) 301) (= (type (cdr item)) 'STR))
       (setq key (cdr item)))
      ((and key (member (car item) '(300 40 90 290)))
       (setq val (cdr item)
             val (cond ((= (type val) 'STR) val)
                       ((= (type val) 'INT) (itoa val))
                       ((= (type val) 'REAL) (rtos val 2 2))
                       ((eq val T) "1")
                       ((null val) "0")
                       (t (vl-princ-to-string val))))
       (setq res (cons (cons key val) res) key nil))))
  (reverse res))

(defun psp-field (fields name / p)
  (setq p (assoc name fields))
  (if p (cdr p)))

(defun psp-spds-row (obj / ent f)
  (setq ent (vlax-vla-object->ename obj)
        f (psp-spds-fields ent))
  (list (if (psp-field f "Format")
          (list (psp-field f "Format") "entget301")
          (psp-spds-prop-ex obj *psp-spds-props-format*))
        (if (psp-field f "Sheet")
          (list (psp-field f "Sheet") "entget301")
          (psp-spds-prop-ex obj *psp-spds-props-sheet*))
        (if (psp-field f "SheetCount")
          (list (psp-field f "SheetCount") "entget301")
          (psp-spds-prop-ex obj *psp-spds-props-total*))
        (psp-spds-bbox obj)))

;; Габариты объекта в WCS: (llx lly urx ury) или nil.

;; GetBoundingBox через vl-catch-all-apply привязывает к символам
;; safearray (иногда variant) — оба варианта разбирает psp-va->list-unwrap.
(defun psp-spds-bbox (obj / mn mx a b)
  (vl-catch-all-apply 'vla-getboundingbox (list obj 'mn 'mx))
  (if (and (boundp 'mn) (boundp 'mx))
    (progn
      (setq a (vl-catch-all-apply 'vlax-safearray->list
                                  (list (psp-va->list-unwrap mn)))
            b (vl-catch-all-apply 'vlax-safearray->list
                                  (list (psp-va->list-unwrap mx))))
      (if (and (not (vl-catch-all-error-p a))
               (not (vl-catch-all-error-p b))
               a b (= (length a) 3) (= (length b) 3))
        (list (car a) (cadr a) (car b) (cadr b))
        nil))
    nil))

;; Нормализация имени формата: верхний регистр, кириллические
;; гомоглифы -> латиница. "А4х3" -> "A4X3".
(defun psp-spds-norm (s / i ch res)
  (setq s (strcase (vl-string-trim " \\t" s)) res "" i 1)
  (while (<= i (strlen s))
    (setq ch (substr s i 1)
          res (strcat res
                (cond
                  ((member ch '("А" "A")) "A")
                  ((member ch '("В" "B")) "B")
                  ((member ch '("С" "C")) "C")
                  ((member ch '("Е" "E")) "E")
                  ((member ch '("Н" "H")) "H")
                  ((member ch '("К" "K")) "K")
                  ((member ch '("М" "M")) "M")
                  ((member ch '("О" "O")) "O")
                  ((member ch '("Р" "P")) "P")
                  ((member ch '("Т" "T")) "T")
                  ((member ch '("У" "Y")) "Y")
                  ((member ch '("Х" "X")) "X")
                  ((member ch '("0" "1" "2" "3" "4"
                                 "5" "6" "7" "8" "9")) ch)
                  (t "")))
          i (1+ i)))
  res)

;; Разбор нормализованного имени: "A4X3" -> ("A4" 3); "2A0" -> ("2A0" 1).
;; База — буквы и цифры до разделителя X; после X — кратность.
(defun psp-spds-parse (norm / k base mult)
  (cond
    ((or (null norm) (= norm "")) nil)
    ((and (setq k (vl-string-search "X" norm)) (> k 0))
     (setq base (substr norm 1 k)
           mult (atoi (substr norm (+ k 2))))
     (if (> mult 0) (list base mult) (list base 1)))
    (t (list norm 1))))

;; Индекс номинала в таблице форматов (по короткому имени).
(defun psp-format-idx (base / i lst found)
  (setq i 0 lst *psp-formats* found nil)
  (while (and lst (not found))
    (if (equal (nth 0 (car lst)) base) (setq found i))
    (setq i (1+ i) lst (cdr lst)))
  found)

;; Бумага «на шаг вверх» по номиналу: A4->A3, A3->A2 ... 4A0->4A0.
;; Возвращает запись *psp-formats* или nil.
(defun psp-spds-size-up (base / idx n)
  (setq idx (psp-format-idx base)
        n (length *psp-formats*))
  (cond
    ((null idx) nil)
    ((>= idx (1- n)) (nth (1- n) *psp-formats*))
    (t (nth (1+ idx) *psp-formats*))))

;; Поиск Ghostscript: переменная *psp-gs* -> портативный gs рядом
;; с чертежом -> реестр -> Program Files. Возвращает путь к консольному
;; gswin64c.exe/gswin32c.exe или nil.
;; Каталог файла: всё до последнего "\\" (вручную, без vl-filename-*:
;; на машине с СПДС хуками vl-filename-directory возвращает T)
(defun psp-file-dir (path / i last)
  (setq i 1 last 0)
  (if (= (type path) 'STR)
    (progn
      (while (<= i (strlen path))
        (if (= (substr path i 1) "\\") (setq last i))
        (setq i (1+ i)))
      (if (> last 0) (substr path 1 (1- last)) ""))))

;; Имя файла без каталога: всё после последнего "\\"
(defun psp-file-base (path / i last)
  (setq i 1 last 0)
  (if (= (type path) 'STR)
    (progn
      (while (<= i (strlen path))
        (if (= (substr path i 1) "\\") (setq last i))
        (setq i (1+ i)))
      (if (> last 0) (substr path (1+ last)) path))))

;; Поиск Ghostscript: переменная *psp-gs* -> gs рядом с чертежом ->
;; реестр (GS_DLL/GS_LIB) -> Program Files. Каждый этап печатает
;; результат (диагностика «gs=T»); наружу только строка или nil.
;; Поиск Ghostscript. Приоритет: явный путь (ПСПГС) -> реестр
;; (GS_DLL/GS_LIB = фактический каталог установки) -> Program Files ->
;; портативный в папке модулей -> пути рядом с чертежом (на веру,
;; последними). Проверок файлов нет (на машине с СПДС findfile/open
;; возвращают T), КРОМЕ портативной ветки: диск выбирается по факту
;; существования папки (vl-file-directory-p — проверен чисто).
(defun psp-find-gs ( / try res brand vk v pd sub exe p)
  (defun try (p)
    (if (= (type p) 'STR) p nil))
  ;; 1) явно задан командой ПСПГС (запоминается в реестре настроек)
  (setq res (try *psp-gs*))
  (if res (princ (strcat "\n  GS[1] задан ПСПГС: " res)))
  ;; 2) реестр: каталог установки из GS_DLL/GS_LIB
  (if (null res)
    (foreach brand (list "GPL Ghostscript" "AFPL Ghostscript" "GNU Ghostscript")
      (if (null res)
        (foreach vk (vl-registry-descendents
                      (strcat "HKEY_LOCAL_MACHINE\\SOFTWARE\\" brand))
          (if (null res)
            (foreach vn (list "GS_DLL" "GS_LIB")
              (if (null res)
                (progn
                  (setq v (vl-registry-read
                            (strcat "HKEY_LOCAL_MACHINE\\SOFTWARE\\"
                                    brand "\\" (vl-princ-to-string vk))
                            vn))
                  (if (= (type v) 'STR)
                    (progn
                      (setq res (or (try (strcat (psp-file-dir v)
                                                 "\\gswin64c.exe"))
                                    (try (strcat (psp-file-dir v)
                                                 "\\gswin32c.exe"))))
                      (if res
                        (princ (strcat "\n  GS[2] реестр "
                                       (vl-princ-to-string vk) "\\" vn
                                       ": " res)))))))))))))
  ;; 3) Program Files: gs\\gs<версия>\\bin
  (if (null res)
    (foreach pd (list "C:\\Program Files\\gs" "C:\\Program Files (x86)\\gs")
      (if (vl-file-directory-p pd)
        (foreach sub (vl-directory-files pd nil -1)
          (if (= (type sub) 'STR)
            (foreach exe (list "gswin64c.exe" "gswin32c.exe")
              (if (null res)
                (progn
                  (setq res (try (strcat pd "\\" sub "\\bin\\" exe)))
                  (if res
                    (princ (strcat "\n  GS[3] Program Files: " res)))))))))))
  ;; 3.5) портативный Ghostscript в папке модулей
  ;;      (<диск>:\PlotFrameToPDF\gs\bin\gswin64c.exe): страховая
  ;;      ветка на случай, когда установленного GS нет (реестр и
  ;;      Program Files пусты); диск — первый, где есть папка
  (if (null res)
    (foreach pd (list "C:" "D:" "E:")
      (if (and (null res)
               (vl-file-directory-p
                 (strcat pd "\\PlotFrameToPDF\\gs\\bin")))
        (progn
          (setq res (try (strcat pd "\\PlotFrameToPDF\\gs\\bin\\gswin64c.exe")))
          (if res (princ (strcat "\n  GS[3.5] портативный: " res)))))))

  ;; 4) рядом с чертежом (пути «на веру»: существуют, только если
  ;;    GS туда действительно клали)
  (if (null res)
    (foreach p (list (strcat (getvar "DWGPREFIX") "gs\\bin\\gswin64c.exe")
                     (strcat (getvar "DWGPREFIX") "gs\\bin\\gswin32c.exe")
                     (strcat (getvar "DWGPREFIX") "gs\\gswin64c.exe")
                     (strcat (getvar "DWGPREFIX") "gs\\gswin32c.exe")
                     (strcat (getvar "DWGPREFIX") "gswin64c.exe")
                     (strcat (getvar "DWGPREFIX") "gswin32c.exe"))
      (if (null res)
        (progn
          (setq res (try p))
          (if res (princ (strcat "\n  GS[4] рядом с чертежом: " res)))))))
  ;; страховка: наружу только строка или nil
  (if (= (type res) 'STR) res nil))

;; Безопасная строка: STR как есть, nil -> "", прочее -> princ-to-string
;; (T и прочие не-строки не роняют strcat). Утеряна срезом 0.32,
;; возвращена в 0.34: во втором чертеже чистое пространство имён
;; показало «no function definition: PSP-S->STR».
(defun psp-s->str (x)
  (cond
    ((= (type x) 'STR) x)
    ((null x) "")
    (t (vl-princ-to-string x))))

;; Только STR, иначе умолчание: T из списков не должен выживать
(defun psp-str-or (v d)
  (if (= (type v) 'STR) v d))

;; Открыть PDF и убрать одиночные листы. Ghostscript создаёт файл
;; выхода СРАЗУ, а закрывает только в конце работы: и открытие, и
;; удаление листов выполняются с задержкой ~5 с (ping) в ОТДЕЛЬНОМ
;; фоновом cmd — AutoCAD не ждёт, gs успевает закрыть файлы.
;; Одиночные листы удаляются ОДНОЙ командой с маской dir\L*.pdf:
;; в папке сборки только листы L*.pdf; альбом называется
;; <имя чертежа>_<дата>_<время>.pdf — под маску L*.pdf не попадает.
;; Цепочка из отдельных del на каждый лист (0.42) не сработала —
;; слишком длинная команда. Запасной путь — explorer (без удаления).
(defun psp-open-pdf (path dir / ok cmd dl)
  (setq dl (itoa (1+ *psp-open-delay-s*)))
  (princ (strcat " (открытие через ~" (itoa *psp-open-delay-s*) " с)"))
  ;; проверка альбома в LISP (в момент фактического открытия):
  ;; нет файла — открывается папка сборки, а не ничего
  (if (findfile (psp-s->str path))
    (progn
      (setq cmd (strcat "ping -n " dl " 127.0.0.1 > nul"))
      (if *psp-del-singles*
        (setq cmd (strcat cmd " & del \"" dir "\\L*.pdf\"")))
      (setq cmd (strcat cmd " & start \"\" \"" path "\""))
      (setq ok (startapp "cmd.exe" (strcat "/c " cmd)))
      (princ (strcat "[cmd=" (psp-s->str ok) "]"))
      (if (null ok)
        (progn
          (setq ok (startapp "explorer.exe" path))
          (princ (strcat "[explorer=" (psp-s->str ok) "]")))))
    (progn
      (princ "\nПСП: альбом не найден — открываю папку сборки.")
      (setq ok (startapp "explorer.exe" dir))
      (princ (strcat "[explorer=" (psp-s->str ok) "]"))))
  ;; Вторая волна: PDF-XChange держит ОТКРЫТЫЕ листы (вкладки), Windows
  ;; не удаляет занятые файлы (подтверждено диагностикой: при закрытом
  ;; просмотрщике del чист, при открытом — ошибки блокировки).
  ;; Повторяем del ~1 минуту (12 x 5 с): листы удалятся, как только
  ;; просмотрщик будет закрыт.
  (if *psp-del-singles*
    (progn
      (princ "\nПСП: листы будут удаляться ещё ~1 мин (если просмотрщик их держал)")
      (startapp "cmd.exe"
                (strcat "/c for /l %i in (1,1,12)"
                        " do @(ping -n " dl " 127.0.0.1 > nul"
                        " & del \"" dir "\\L*.pdf\" 2>nul)"))))
  ok)

(defun psp-merge-pdfs (gs src-lst trg / cmd k s prev cur stable)
  ;; диагностика: размер каждого входа (0 байт = страница выпадет)
  (foreach s src-lst
    (princ (strcat "\n  вход " (psp-s->str s) ": "
                   (if (findfile (psp-s->str s))
                     (strcat (itoa (vl-file-size (psp-s->str s)))
                             " байт")
                     "НЕТ"))))
  (setq cmd (strcat "\"" (psp-s->str gs) "\""
                    " -dBATCH -dNOPAUSE -dSAFER -dQUIET -sDEVICE=pdfwrite"
                    " -sOutputFile=\"" (psp-s->str trg) "\""))
  (foreach s src-lst
    (setq cmd (strcat cmd " \"" (psp-s->str s) "\"")))
  (startapp cmd)
  ;; GS создаёт файл СРАЗУ, а дописывает последним: ждать не появле-
  ;; ния, а СТАБИЛИЗАЦИИ размера (иначе зритель открывал недописан-
  ;; ный альбом — «склеилось 5/6 из 7»)
  (setq k 0 prev -1 cur -1 stable 0)
  (while (and (< stable 3) (< k 60))
    (psp-sleep 500)
    (setq cur (if (findfile trg)
                (vl-file-size (psp-s->str trg)) -1))
    (if (and (> cur 0) (= cur prev))
      (setq stable (1+ stable))
      (setq stable 0))
    (setq prev cur k (1+ k)))
  (if (> cur 0)
    (princ (strcat "\n  размер альбома: " (itoa cur) " байт")))
  (if (> cur 0) trg nil))

;; ---------------------------------------------------------------------------
;; СПДС: сортировка и имена

;; ---------------------------------------------------------------------------

(defun psp-pad2 (n)
  (if (< n 10) (strcat "0" (itoa n)) (itoa n)))

;; Номер листа как число: "15" -> 15.0, "15.1" -> 15.1 (запятая тоже
;; понимается); nil/пустое -> 0 (без номера). Дробные листы (15, 15.1,
;; 15.2) сортируются по возрастанию: 15 < 15.1 < 15.2.
(defun psp-sheet-num (s)
  (if (= (type s) 'STR)
    (atof (vl-string-translate "," "." s))
    0.0))

;; T: строка номера листа — настоящий номер (непустая и состоит
;; только из цифр, точек и запятых). "0" -> T (титульный лист),
;; "15.1" -> T, nil/""/"А" -> nil (лист считается безномерным).
(defun psp-sheet-p (s / i n ch ok)
  (if (= (type s) 'STR)
    (progn
      (setq s (vl-string-trim " " s)
            i 1
            n (strlen s)
            ok (> n 0))
      (while (and ok (<= i n))
        (setq ch (substr s i 1))
        (if (not (or (= ch ".") (= ch ",")
                     (and (>= ch "0") (<= ch "9"))))
          (setq ok nil))
        (setq i (1+ i)))
      ok)
    nil))

;; Имя файла из строки номера СПДС: "15" -> "L15" (целая часть
;; дополняется до двух знаков: "9" -> "L09"), "15.1" -> "L15.1",
;; запятая заменяется точкой.
(defun psp-sheet-name (s / norm k)
  (if (= (type s) 'STR)
    (progn
      (setq norm (vl-string-trim " " (vl-string-translate "," "." s)))
      (if (= norm "")
        nil
        (if (setq k (vl-string-search "." norm))
          (strcat "L" (substr norm 1 k) (substr norm (1+ k)))
          (strcat "L" (psp-pad2 (atoi norm))))))
    nil))

;; Число для отчёта: целое вещественное печатается без ".0"
(defun psp-num-str (n)
  (if (and (= (type n) 'REAL) (= n (float (fix n))))
    (itoa (fix n))
    (vl-princ-to-string n)))

;; Уникальное имя: s01; повторы -> s01_2, s01_3 ...
(defun psp-spds-uniq (base used / nm k)
  (setq nm base k 1)
  (while (member nm used)
    (setq k (1+ k) nm (strcat base "_" (itoa k))))
  (list nm (cons nm used)))

;; Порядок «меньше» для печати: лист по возрастанию; без номера —
;; в конец; внутри — сверху вниз (lly = nth 5, убывает), затем
;; слева направо (llx = nth 4, возрастает).
(defun psp-spds-less (a b)
  (cond
    ((< (nth 3 a) (nth 3 b)) T)
    ((> (nth 3 a) (nth 3 b)) nil)
    ((> (nth 5 a) (nth 5 b)) T)
    ((< (nth 5 a) (nth 5 b)) nil)
    (t (< (nth 4 a) (nth 4 b)))))

;; Сортировка вставкой (списки небольшие).
(defun psp-spds-sorted (items / res it head rest done)
  (setq res nil)
  (foreach it items
    (setq head nil rest res done nil)
    (while (and rest (not done))
      (if (psp-spds-less it (car rest))
        (setq done T)
        (setq head (cons (car rest) head) rest (cdr rest))))
    (setq res (append (reverse head) (list it) rest)))
  res)
;; ---------------------------------------------------------------------------
;; Команда: ЭКССПДСПДФ / EXPSPDSPDF

;; ---------------------------------------------------------------------------

(defun c:ЭКССПДСПДФ ( / ss n i ent obj it items fmt sheet sheet-i
                          bb used rec media rot-str ctb dir stamp fname
                          nm-n w h x1 y1 x2 y2 ok-list skip j row flds mult multv
                          old-bg old-paper old-trans has-trans res
                          merge-list gs ans merged pdfs k chk auto-merge
                          dwgn)
  (princ "\nЭкспорт форматов СПДС в PDF. Выберите объекты (или All).")
  (setq ss (ssget (list (cons 0 *psp-spds-entity*))))
  (cond
    ((null ss) (princ "\nОтменено.") (princ))
    (t
     ;; Сбор сведений
     (setq n (sslength ss) i 0 items nil skip nil)
     (princ (strcat "\nПСП: выбрано объектов: " (itoa n)))
     (while (< i n)
       (setq ent (ssname ss i))
       (setq obj (vlax-ename->vla-object ent))
       (setq flds (psp-spds-fields ent))
       (setq fmt (psp-field flds "Format"))
       (if (null fmt)
         (setq fmt (psp-spds-prop obj *psp-spds-props-format*)))
       (setq sheet (psp-field flds "Sheet"))
       (if (null sheet)
         (setq sheet (psp-spds-prop obj *psp-spds-props-sheet*)))
       (setq sheet-i (psp-sheet-num sheet))
       (setq bb (psp-spds-bbox obj))
       ;; кратность: A4 + Multiplicity 3 -> "A4X3" (бумага на 3 шага вверх)
       (setq multv (psp-field flds "Multiplicity"))
       (if (/= (type multv) 'STR) (setq multv "1"))
       (setq mult (atoi multv))
       (if (and fmt (> mult 1))
         (setq fmt (strcat fmt "X" (itoa mult))))
       (if bb
         (setq items
               (cons (list ent obj fmt
                           (if (psp-sheet-p sheet) sheet-i 9999.0)
                           (car bb) (cadr bb) (caddr bb) (cadddr bb)
                           sheet)
                     items))
         (setq skip (cons (cdr (assoc 5 (entget ent))) skip)))
       (setq i (1+ i)))
     (setq items (psp-spds-sorted (reverse items)))
     (princ (strcat "\nПСП: к печати после сортировки: " (itoa (length items))))
     (cond
       ((null items)
        (princ "\nУ выбранных объектов нет габаритов — печатать нечего.")
        (princ))
       (t
        ;; Папка сборки: <имя чертежа> (без даты); альбом внутри:
        ;; <имя>_<дата>_<время>.pdf — повторные сборки накапливаются
        ;; в одной папке. (DWGNAME минус расширение; DWGTITLED —
        ;; только флаг 0/1, именем служить не может)
        (setq stamp (rtos (getvar "CDATE") 2 6)
              dwgn (getvar "DWGNAME"))
        (if (/= (type dwgn) 'STR) (setq dwgn ""))
        (setq k (strlen dwgn))
        ;; точка трёхсимвольного расширения — на позиции k-3
        (if (and (> k 4) (= (substr dwgn (- k 3) 1) "."))
          (setq dwgn (substr dwgn 1 (- k 4))))
        (if (= dwgn "") (setq dwgn "SPDS"))
        (setq dir (strcat (psp-output-dir) "\\" dwgn))
        (if (not (vl-file-directory-p dir)) (vl-mkdir dir))
        (princ (strcat "\nПСП: папка сборки: " dir))
        (setq ctb (if *psp-color-mode* *psp-ctb-color* *psp-ctb-mono*))
        ;; Системные переменные: сохранить -> изменить -> восстановить
        (setq has-trans
              (not (vl-catch-all-error-p
                     (vl-catch-all-apply
                       'getvar '("PLOTTRANSPARENCYOVERRIDE")))))
        (if has-trans (setq old-trans (getvar "PLOTTRANSPARENCYOVERRIDE")))
        (setq old-bg (getvar "BACKGROUNDPLOT"))
        (setq old-paper (vl-catch-all-apply 'getvar (list "PAPERUPDATE")))
        (psp-clear-stuck)
        (setvar "BACKGROUNDPLOT" 0)
        ;; 0 = не спрашивать "Сохранить изменения параметров листа?"/
        ;; "Перейти к печати?" при несовпадении размеров (первая печать
        ;; в свежем чертеже без лишних подтверждений)
        (if (not (vl-catch-all-error-p old-paper))
          (setvar "PAPERUPDATE" 0))


        (princ (strcat "\nПСП: PAPERUPDATE="
                       (itoa (getvar "PAPERUPDATE"))
                       " BACKGROUNDPLOT="
                       (itoa (getvar "BACKGROUNDPLOT"))
                       (if *psp-plot-echo* " (эхо=вкл)" " (эхо=выкл)")))
        (if (and (not (vl-catch-all-error-p old-paper))
                 (/= (getvar "PAPERUPDATE") 0))
          (princ "\nПСП: ВНИМАНИЕ: PAPERUPDATE не принят = 0!"))
        (if has-trans (setvar "PLOTTRANSPARENCYOVERRIDE" 1))
        ;; Цикл печати
        (setq used nil ok-list nil j 0)
        (foreach it items
          (setq w (- (nth 6 it) (nth 4 it))
                h (- (nth 7 it) (nth 5 it))
                rec (if (nth 2 it)
                      (car (psp-spds-parse (psp-spds-norm (nth 2 it)))))
                rec (cond
                      ((null rec) nil)
                      ((= *psp-quality* 0)
                       (if (psp-format-idx rec)
                         (nth (psp-format-idx rec) *psp-formats*)
                         nil))
                      ((= *psp-quality* 2)
                       (psp-spds-size-up
                         (nth 0 (psp-spds-size-up rec))))
                      (t (psp-spds-size-up rec)))
                rec (if rec rec (nth 3 *psp-formats*))
                media (if (>= w h) (nth 4 rec) (nth 3 rec))
                rot-str (if (>= w h) "_L" "_P")
                nm-n (psp-spds-uniq
                       (if (nth 8 it)
                         (psp-sheet-name (nth 8 it))
                         (strcat "L" (psp-pad2 (1+ j))))
                       used)
                fname (strcat dir "\\" (car nm-n))
                used (cadr nm-n))
          (princ (strcat "\n  ПСП: " (car nm-n) " (" media ")"))
          ;; Предустановка формата листа (без лишних вопросов)
          (setq *psp-stage* "предустановка листа")
          (setq res (vl-catch-all-apply 'psp-page-preset (list media)))
          (if (vl-catch-all-error-p res)
            (progn
              (princ "\n  ПСП: предустановка ОШИБКА: ")
              (princ (vl-catch-all-error-message res)))
            (progn
              (setq chk (vl-catch-all-apply 'psp-get (list
                          (psp-get (psp-get (vlax-get-acad-object)
                                            'ActiveDocument) 'ActiveLayout)
                          'CanonicalMediaName)))
              (princ (strcat "\n  ПСП: предустановка: "
                             (if (and (= (type chk) 'STR) (/= chk ""))
                               chk "НЕ ПРИМЕНИЛАСЬ")
                             (if (and (= (type chk) 'STR)
                                      (/= (strcase chk)
                                          (strcase media)))
                               " (ВНИМАНИЕ: не запрошенная!)"
                               "")))))
          ;; Окно печати задаётся в UCS
          (setq x1 (car (trans (list (nth 4 it) (nth 5 it)) 0 1))
                y1 (cadr (trans (list (nth 4 it) (nth 5 it)) 0 1))
                x2 (car (trans (list (nth 6 it) (nth 7 it)) 0 1))
                y2 (cadr (trans (list (nth 6 it) (nth 7 it)) 0 1)))
          (setq *psp-stage* "печать листа")
          (setq res (vl-catch-all-apply 'psp-plot-tape
                      (list (strcat fname ".pdf") media rot-str ctb
                            x1 y1 x2 y2 chk nil)))
          (psp-page-restore)
          ;; Если -ПЕЧАТЬ застряла на незапланированном вопросе, в стеке
          ;; остаётся CMDACTIVE; его остатки сдвинули бы следующую ленту.
          ;; Снимаем по ESC (без пустых Enter) и пропускаем лист.
          (if (> (getvar "CMDACTIVE") 0)
            (progn
              (princ "\n  ПСП: -ПЕЧАТЬ застряла на вопросе, снимаю по ESC.")
              (princ "\n  ПСП: для диагностики включите ПСПЭХОВКЛ и повторите.")
              (psp-clear-stuck))
            (if (vl-catch-all-error-p res)
              (princ "  ошибка печати, см. ниже")
              (princ "  отправлено на печать.")))
          ;; Вторая попытка ТОЛЬКО для листа: если PDF не появился,
          ;; значит лист был «грязный» и -ПЕЧАТЬ задала лишний вопрос
          ;; («записать изменения в макет») — повтор с 4-м «Нет».
          (if (and (= (getvar "TILEMODE") 0)
                   (not (findfile (strcat fname ".pdf"))))
            (progn
              (princ "\n  ПСП: PDF не появился — вторая попытка (плюс «Нет» на «записать изменения»).")
              (vl-catch-all-apply 'psp-page-preset (list media))
              (setq res (vl-catch-all-apply 'psp-plot-tape
                          (list (strcat fname ".pdf") media rot-str ctb
                                x1 y1 x2 y2 chk T)))
              (psp-page-restore)
              (if (> (getvar "CMDACTIVE") 0) (psp-clear-stuck))))
          (if (and (vl-catch-all-error-p res)
                   (= (getvar "CMDACTIVE") 0))
            (progn
              (princ (strcat "\nПСП: ОШИБКА [этап: " *psp-stage*
                             "] — " (vl-catch-all-error-message res)))
              (setq skip (cons (car nm-n) skip)))
            (if (findfile (strcat fname ".pdf"))
              (setq ok-list
                    (cons (list (car nm-n) (nth 2 it) (nth 3 it)
                                (if (and (= (type chk) 'STR)
                                         (/= chk ""))
                                  chk media))
                          ok-list)
                    merge-list (cons (strcat (car nm-n) ".pdf")
                                     merge-list))
              (progn
                (princ (strcat "\n  ПСП: PDF не найден, ожидался: "
                               fname ".pdf"))
                (setq skip (cons (car nm-n) skip)))))
          (setq j (1+ j)))
        ;; Восстановление системных переменных
        (if has-trans (setvar "PLOTTRANSPARENCYOVERRIDE" old-trans))
        (setvar "BACKGROUNDPLOT" old-bg)
        (if (not (vl-catch-all-error-p old-paper))
          (setvar "PAPERUPDATE" old-paper))
        ;; Отчёт
        (setq ok-list (reverse ok-list))
        (princ (strcat "\nСборка: " dir))
        (princ "\n  | файл   | формат СПДС | лист | бумага PDF    |")
        (princ "\n  |--------|-------------|------|---------------|")
        (foreach row ok-list
          (princ (strcat "\n  | "
                         (psp-pad-right (nth 0 row) 6)
                         " | "
                         (psp-pad-right (if (nth 1 row) (nth 1 row) "-") 11)
                         " | "
                         (if (< (nth 2 row) 9999) (psp-num-str (nth 2 row)) "-")
                         "    | "
                         (psp-pad-right (nth 3 row) 13)
                         " |")))
        (princ (strcat "\nГотово: " (itoa (length ok-list))
                       " из " (itoa (length items))
                       "; без габаритов/ошибок: " (itoa (length skip))))
        ;; Сборка в один многостраничный PDF (если есть Ghostscript
        ;; и напечатано больше одного листа)
        (setq gs (if (> (length ok-list) 1)
                   (vl-catch-all-apply 'psp-find-gs nil)))
        (if (vl-catch-all-error-p gs)
          (progn
            (princ "\nПСП: поиск Ghostscript ОШИБКА: ")
            (princ (vl-catch-all-error-message gs))
            (setq gs nil)))
        (setq auto-merge (> (length ok-list) *psp-auto-merge-n*))
        (if (and (> (length ok-list) 1) gs)
          (progn
            (if auto-merge
              (progn
                (setq ans "Да")
                (princ (strcat "\nПСП: листов " (itoa (length ok-list))
                               " (>3) — собираю в один PDF автоматически.")))
              (progn
                (initget "Да Нет _ Yes No")
                (setq ans (getkword "\nСобрать все листы в один PDF? [Да/Нет] <Да>: "))
                (if (null ans) (setq ans "Да"))))
            (if (member (strcase ans)
                        (list (strcase "Да") (strcase "Yes")))
              (progn
                ;; полные пути: gs ищет входные файлы в СВОЁМ рабочем
                ;; каталоге, голые имена не находит (пустая страница)
                (setq pdfs (mapcar
                             '(lambda (f) (strcat dir "\\" f))
                             (reverse merge-list))
                      merged (strcat dir "\\" dwgn "_"
                                     (substr stamp 1 8) "_"
                                     (substr stamp 10 6) ".pdf"))
                (princ (strcat "\nПСП: склеиваю " (itoa (length pdfs))
                               " листов (Ghostscript)..."))
                (princ (strcat "\n  gs=" (psp-s->str gs)))
                (princ (strcat "\n  out=" (psp-s->str merged)))
                (setq res (vl-catch-all-apply
                            'psp-merge-pdfs (list gs pdfs merged)))
                (cond
                  ((vl-catch-all-error-p res)
                   (princ "\nПСП: склейка ОШИБКА: ")
                   (princ (vl-catch-all-error-message res)))
                  ((null res)
                   (princ (strcat "\nПСП: файл не появился за 20 с — "
                                  "проверьте gs вручную: " (psp-s->str gs))))
                  (t
                   (princ (strcat "\nСобрано в один PDF: " (psp-s->str res)))
(if *psp-open-res*
                     (progn
                       (princ "\nПСП: открываю в просмотрщике PDF...")
                       (if *psp-del-singles*
                         (princ (strcat "\nПСП: одиночные листы удаляются ("
                                        (itoa (length pdfs)) " шт.)")))
                       (psp-open-pdf (psp-s->str res) dir))))))
              (progn
                (princ "\nПСП: сборка в один PDF пропущена.")
                (if *psp-open-res*
                  (progn
                    (princ (strcat "\nПСП: открываю одиночные листы ("
                                   (itoa (length merge-list))
                                   " шт.) через ~" (itoa *psp-open-delay-s*) " с"))
                    (startapp "cmd.exe"
                              (strcat "/c ping -n "
                                      (itoa (1+ *psp-open-delay-s*))
                                      " 127.0.0.1 > nul"
                                      (apply 'strcat
                                             (mapcar
                                               '(lambda (f)
                                                  (strcat " & start \"\" \""
                                                          dir "\\" f "\""))
                                               (reverse merge-list))))))))))
          (if (> (length ok-list) 1)
            (princ "\nПСП: Ghostscript не найден — один PDF не собираю.\nПСП: установите GS или задайте путь командой ПСПГС.")))
        ;; Один лист без склейки: он и есть результат — открываем
        (if (and *psp-open-res* (= (length ok-list) 1))
          (startapp "cmd.exe"
                    (strcat "/c ping -n " (itoa (1+ *psp-open-delay-s*))
                            " 127.0.0.1 > nul & start \"\" \""
                            dir "\\" (nth 0 (car ok-list)) ".pdf\"")))
        ;; Открыть папку сборки
        (psp-sleep *psp-open-delay*)
        (psp-open dir)
        (princ)))))
  (princ))
(defun c:EXPSPDSPDF () (c:ЭКССПДСПДФ))
;; Открыть папку журналов и сборок в Проводнике
;; Чтение тайлов в callback кнопки «Применить»: после закрытия
;; диалога get_tile в ряде версий AutoCAD уже не действует
;; Список PDF-принтеров: все .pc3 из папки конфигураций плоттеров
(defun psp-pc3-list ( / d lst)
  (setq d (getenv "PrinterConfigDir"))
  (if (= (type d) 'STR)
    (progn
      (setq lst (vl-catch-all-apply
                  'vl-directory-files (list d "*.pc3" 1)))
      (if (not (listp lst)) (setq lst nil))))
  (if lst
    (setq lst (vl-sort lst
                (function (lambda (a b) (< (strcase a) (strcase b))))))
    (setq lst (list "DWG To PDF.pc3")))
  (if (not (member (strcase (if *psp-pc3* *psp-pc3* "") T)
                   (mapcar '(lambda (x) (strcase x T)) lst)))
    (setq lst (cons (if *psp-pc3* *psp-pc3* "PlotSPDSToPDF.pc3") lst)))
  lst)

;; Список CTB (стилей печати) из папки стилей AutoCAD
(defun psp-ctb-list ( / d lst cur)
  (setq d (getenv "PrinterStyleSheetDir"))
  (if (= (type d) 'STR)
    (progn
      (setq lst (vl-catch-all-apply
                  'vl-directory-files (list d "*.ctb" 1)))
      (if (not (listp lst)) (setq lst nil))))
  (if lst
    (setq lst (vl-sort lst
                (function (lambda (a b) (< (strcase a) (strcase b))))))
    (setq lst (list "monochrome.ctb" "acad.ctb")))
  (foreach cur (list (if (boundp '*pfp-ctb-mono*) *pfp-ctb-mono*)
                     (if (boundp '*pfp-ctb-color*) *pfp-ctb-color*))
    (if (and (= (type cur) 'STR) (/= cur "")
             (not (member (strcase cur T)
                          (mapcar '(lambda (x) (strcase x T)) lst))))
      (setq lst (cons cur lst))))
  lst)

;; Список СИСТЕМНЫХ принтеров Windows (для FP-модуля): ключи
;; HKLM\SYSTEM\CurrentControlSet\Control\Print\Printers;
;; FinePrint добавляется, если его нет; текущие значения тоже
(defun psp-printer-list ( / lst s cur)
  (setq lst (vl-catch-all-apply 'vl-registry-descendents
              (list "HKEY_LOCAL_MACHINE\\SYSTEM\\CurrentControlSet\\Control\\Print\\Printers")))
  (if (not (listp lst)) (setq lst nil))
  (setq s nil)
  (foreach x lst
    (if (and (= (type x) 'STR) (/= x "")
             (not (member (strcase x T) (mapcar '(lambda (y) (strcase y T)) s))))
      (setq s (cons x s))))
  (setq s (vl-sort s (function (lambda (a b) (< (strcase a) (strcase b))))))
  (if (not (member (strcase "FinePrint" T)
                   (mapcar '(lambda (y) (strcase y T)) s)))
    (setq s (cons "FinePrint" s)))
  (foreach cur (list (getcfg "AppData/PlotFrame/FPPrinterA4")
                     (getcfg "AppData/PlotFrame/FPPrinterA3"))
    (if (and (= (type cur) 'STR) (/= cur "")
             (not (member (strcase cur T)
                          (mapcar '(lambda (y) (strcase y T)) s))))
      (setq s (cons cur s))))
  (if (null s) (setq s (list "FinePrint")))
  s)

;; Заполнить выпадающий список и выбрать текущее значение
(defun psp-popup-fill (key lst cur / idx s keep)
  ;; только строки; cur через psp-s->str: ошибка типа здесь не нужна
  (setq keep nil)
  (foreach s lst
    (if (= (type s) 'STR) (setq keep (cons s keep))))
  (setq keep (reverse keep) cur (psp-s->str cur) idx 0)
  (start_list key)
  (foreach s keep (add_list s))
  (end_list)
  (while (and keep (/= (strcase (car keep) T) (strcase cur T)))
    (setq keep (cdr keep) idx (1+ idx)))
  (if (null keep) (setq idx 0))
  (set_tile key (itoa idx))
  (princ))

;; Кнопка «Обзор...»: диалог выбора папки Windows (проводник)
(defun psp-browse-folder ( / sh hw fld pth)
  (setq sh (vl-catch-all-apply
             'vlax-create-object (list "Shell.Application")))
  (if (and sh (not (vl-catch-all-error-p sh)))
    (progn
      (setq hw (vl-catch-all-apply
                 'vlax-get (list (vlax-get-acad-object) 'HWND)))
      (if (/= (type hw) 'INT) (setq hw 0))
      (setq fld (vl-catch-all-apply
                  'vlax-invoke
                  (list sh 'BrowseForFolder hw "Выберите папку для PDF" 0)))
      (if (and fld (not (vl-catch-all-error-p fld)))
        (progn
          (setq pth (vl-catch-all-apply
                      'vlax-get (list (vlax-get fld 'Self) 'Path)))
          (if (and (= (type pth) 'STR) (/= pth "") (/= ":" (substr pth 1 1)))
            (set_tile "dir" pth))
          (vl-catch-all-apply 'vlax-release-object (list fld)))))
    (princ "\nПСП: диалог папок недоступен — введите путь вручную."))
  (if (and sh (not (vl-catch-all-error-p sh)))
    (vl-catch-all-apply 'vlax-release-object (list sh)))
  (princ))

(defun psp-tiles-read ( )
  (setq *psp-t-dir*   (psp-s->str (get_tile "dir"))
        *psp-t-pc3*   (psp-str-or
                        (nth (atoi (get_tile "pc3list")) *psp-t-pc3s*)
                        (psp-str-or *psp-pc3* "PlotSPDSToPDF.pc3"))
        *psp-t-pcol*  (= (psp-s->str (get_tile "mcol")) "1")
        *psp-t-ctbm*  (psp-str-or
                        (nth (atoi (get_tile "ctbm")) *psp-t-ctbs*)
                        "monochrome.ctb")
        *psp-t-ctbc*  (psp-str-or
                        (nth (atoi (get_tile "ctbc")) *psp-t-ctbs*)
                        "acad.ctb")
        *psp-t-fpp4*  (psp-str-or
                        (nth (atoi (get_tile "fpp4")) *psp-t-fpps*)
                        "FinePrint")
        *psp-t-fpp3*  (psp-str-or
                        (nth (atoi (get_tile "fpp3")) *psp-t-fpps*)
                        "FinePrint")
        *psp-t-thr*   (atoi (psp-s->str (get_tile "thr")))
        *psp-t-delay* (atoi (psp-s->str (get_tile "delay")))
        *psp-t-openres* (= (psp-s->str (get_tile "openres")) "1")
        *psp-t-dels*    (= (psp-s->str (get_tile "dels")) "1")
        *psp-t-quality* (cond ((= (psp-s->str (get_tile "q0")) "1") 0)
                              ((= (psp-s->str (get_tile "q2")) "1") 2)
                              (t 1))
        *psp-t-pfq*     (cond ((= (psp-s->str (get_tile "rq0")) "1") 0)
                              ((= (psp-s->str (get_tile "rq2")) "1") 2)
                              (t 1)))
  (princ))

;; Диалог настроек (DCL генерируется во временную папку при вызове)
(defun psp-settings-dialog ( / f dcl d id s n res st)
  (setq dcl (strcat (getenv "TEMP") "\\PlotSPDSToPDF_settings.dcl"))
  (setq f (open dcl "w"))
  ;; v0.80: сетка — каждая строка = [текст 30, вправо][поле 30];
  ;; принтеры PDF/A4/A3 — сверху одной колонкой; цвет — пара радио
  (write-line "psp_set : dialog { label = \"Настройки печати\";" f)
  (write-line "  : boxed_column { label = \"Папка сохранения\";" f)
  (write-line "    : row {" f)
  (write-line "      : edit_box { key = \"dir\"; edit_width = 60; fixed_width = true; }" f)
  (write-line "    }" f)
  (write-line "    : row {" f)
  (write-line "      : text { label = \"(пусто = временная папка сборок)\"; }" f)
  (write-line "      : button { key = \"browse\"; label = \"Обзор...\"; width = 10; fixed_width = true; }" f)
  (write-line "    }" f)
  (write-line "  }" f)
  (write-line "  : boxed_column { label = \"Цвет и стили печати\";" f)
  (write-line "    : row {" f)
  (write-line "      : text { label = \"Принтер PDF:\"; width = 30; fixed_width = true; alignment = right; }" f)
  (write-line "      : popup_list { key = \"pc3list\"; width = 30; fixed_width = true; }" f)
  (write-line "    }" f)
  (write-line "    : row {" f)
  (write-line "      : text { label = \"Принтер A4:\"; width = 30; fixed_width = true; alignment = right; }" f)
  (write-line "      : popup_list { key = \"fpp4\"; width = 30; fixed_width = true; }" f)
  (write-line "    }" f)
  (write-line "    : row {" f)
  (write-line "      : text { label = \"Принтер A3:\"; width = 30; fixed_width = true; alignment = right; }" f)
  (write-line "      : popup_list { key = \"fpp3\"; width = 30; fixed_width = true; }" f)
  (write-line "    }" f)
  (write-line "    : radio_column {" f)
  (write-line "      : radio_button { key = \"cmb\"; label = \"Чёрно-белая печать\"; }" f)
  (write-line "      : radio_button { key = \"mcol\"; label = \"Цветная печать\"; }" f)
  (write-line "    }" f)
  (write-line "    : row {" f)
  (write-line "      : text { label = \"Чёрно-белая печать:\"; width = 30; fixed_width = true; alignment = right; }" f)
  (write-line "      : popup_list { key = \"ctbm\"; width = 30; fixed_width = true; }" f)
  (write-line "    }" f)
  (write-line "    : row {" f)
  (write-line "      : text { label = \"Цветная печать:\"; width = 30; fixed_width = true; alignment = right; }" f)
  (write-line "      : popup_list { key = \"ctbc\"; width = 30; fixed_width = true; }" f)
  (write-line "    }" f)
  (write-line "  }" f)
  (write-line "  : boxed_column { label = \"Сборка и результат\";" f)
  (write-line "    : row {" f)
  (write-line "      : text { label = \"Автосборка при листах БОЛЬШЕ:\"; width = 30; fixed_width = true; alignment = right; }" f)
  (write-line "      : edit_box { key = \"thr\"; edit_width = 30; fixed_width = true; }" f)
  (write-line "    }" f)
  (write-line "    : row {" f)
  (write-line "      : text { label = \"Задержка открытия, с:\"; width = 30; fixed_width = true; alignment = right; }" f)
  (write-line "      : edit_box { key = \"delay\"; edit_width = 30; fixed_width = true; }" f)
  (write-line "    }" f)
  (write-line "    : toggle { key = \"openres\"; label = \"Открывать результат (склейку / одиночные)\"; }" f)
  (write-line "    : toggle { key = \"dels\"; label = \"Удалять одиночные листы после склейки\"; }" f)
  (write-line "  }" f)
  (write-line "  : boxed_column { label = \"Качество печати \\\"Рамка в PDF\\\" (ЭКСПДФ)\";" f)
  (write-line "    : radio_row {" f)
  (write-line "      : radio_button { key = \"rq0\"; label = \"Низкое (-1)\"; width = 23; fixed_width = true; }" f)
  (write-line "      : radio_button { key = \"rq1\"; label = \"Среднее\"; width = 16; fixed_width = true; }" f)
  (write-line "      : radio_button { key = \"rq2\"; label = \"Высокое (+1)\"; width = 16; fixed_width = true; }" f)
  (write-line "    }" f)
  (write-line "  }" f)
  (write-line "  : boxed_column { label = \"Качество печати \\\"Рамка СПДС в PDF\\\" (ЭКССПДСПДФ)\";" f)
  (write-line "    : radio_row {" f)
  (write-line "      : radio_button { key = \"q0\"; label = \"Низкое (по формату)\"; width = 23; fixed_width = true; }" f)
  (write-line "      : radio_button { key = \"q1\"; label = \"Среднее (+1)\"; width = 16; fixed_width = true; }" f)
  (write-line "      : radio_button { key = \"q2\"; label = \"Высокое (+2)\"; width = 16; fixed_width = true; }" f)
  (write-line "    }" f)
  (write-line "  }" f)
  (write-line "  : row { spacer;" f)
  (write-line "    : button { key = \"ok\"; label = \"Применить\"; is_default = true; }" f)
  (write-line "    : button { key = \"cancel\"; label = \"Отмена\"; is_cancel = true; }" f)
  (write-line "    spacer; } }" f)
  (close f)
  (setq d (load_dialog dcl))
  (if (null (new_dialog "psp_set" d))
    (progn
      (unload_dialog d)
      (princ (strcat "\nПСП: диалог настроек не открылся (" dcl ").")))
    (progn
      (setq st "заполнение списков")
      (set_tile "dir" (psp-s->str (if *psp-pdf-dir* *psp-pdf-dir* "")))
      (setq *psp-t-pc3s* (psp-pc3-list))
      (psp-popup-fill "pc3list" *psp-t-pc3s* *psp-pc3*)
      (set_tile "cmb" (if *psp-color-mode* "0" "1"))
      (set_tile "mcol" (if *psp-color-mode* "1" "0"))
      (setq *psp-t-ctbs* (psp-ctb-list))
      (psp-popup-fill "ctbm" *psp-t-ctbs*
        (if *psp-ctb-mono* *psp-ctb-mono* "monochrome.ctb"))
      (psp-popup-fill "ctbc" *psp-t-ctbs*
        (if *psp-ctb-color* *psp-ctb-color* "acad.ctb"))
      (setq *psp-t-fpps* (psp-printer-list))
      (setq s (getcfg "AppData/PlotFrame/FPPrinterA4"))
      (psp-popup-fill "fpp4" *psp-t-fpps*
        (if (and (= (type s) 'STR) (/= s "")) s "FinePrint"))
      (setq s (getcfg "AppData/PlotFrame/FPPrinterA3"))
      (psp-popup-fill "fpp3" *psp-t-fpps*
        (if (and (= (type s) 'STR) (/= s "")) s "FinePrint"))
      (set_tile "thr" (itoa *psp-auto-merge-n*))
      (set_tile "delay" (itoa *psp-open-delay-s*))
      (set_tile "openres" (if *psp-open-res* "1" "0"))
      (set_tile "dels" (if *psp-del-singles* "1" "0"))
      (set_tile "q0" (if (= *psp-quality* 0) "1" "0"))
      (set_tile "q1" (if (= *psp-quality* 1) "1" "0"))
      (set_tile "q2" (if (= *psp-quality* 2) "1" "0"))
      (setq s (getcfg "AppData/PlotFrame/Quality"))
      (setq n (if (= (type s) 'STR) (atoi s) 1))
      (if (not (and (>= n 0) (<= n 2))) (setq n 1))
      (set_tile "rq0" (if (= n 0) "1" "0"))
      (set_tile "rq1" (if (= n 1) "1" "0"))
      (set_tile "rq2" (if (= n 2) "1" "0"))
      (mode_tile "dir" 2)
      (action_tile "browse" "(psp-browse-folder)")
      (action_tile "ok" "(psp-tiles-read)(done_dialog 1)")
      ;; Всё вплоть до конца Apply — под страховкой: ошибка НЕ долж-
      ;; на оставлять диалог открытым (живой диалог блокирует -ПЕЧАТЬ)
      (setq res (vl-catch-all-apply
                  '(lambda ( )
                     (progn
      (setq st "диалог")
      (setq id (start_dialog))
      (setq st "сохранение настроек")
      (if (= id 1)
        (progn
          (setq s *psp-t-dir*)
          (while (and (> (strlen s) 0) (= (substr s (strlen s) 1) "\\"))
            (setq s (substr s 1 (1- (strlen s)))))
          (setq *psp-pdf-dir* s *psp-output-dir* (if (/= s "") s nil))
          (setcfg "AppData/PlotSPDS/PDFDir" s)
          (setcfg "AppData/PlotFrame/OutDir" s)
          (setq *pfp-output-dir* (if (/= s "") s nil))
          (setq s (psp-s->str *psp-t-pc3*))
          (if (not (wcmatch (strcase s T) "*`.pc3"))
            (setq s "PlotSPDSToPDF.pc3"))
          (setq *psp-pc3* s)
          (setcfg "AppData/PlotSPDS/PC3" s)
          ;; Параметры печати базы (задача 12): цвет + CTB
          (setcfg "AppData/PlotFrame/ColorMode"
                  (if *psp-t-pcol* "1" "0"))
          (setcfg "AppData/PlotFrame/CtbMono" (psp-s->str *psp-t-ctbm*))
          (setcfg "AppData/PlotFrame/CtbColor" (psp-s->str *psp-t-ctbc*))
          ;; Принтеры FP-модуля (ЭКСФПА4 / ЭКСФПА3)
          (setcfg "AppData/PlotFrame/FPPrinterA4"
                  (psp-s->str *psp-t-fpp4*))
          (setcfg "AppData/PlotFrame/FPPrinterA3"
                  (psp-s->str *psp-t-fpp3*))
          ;; СПДС печатает по *psp-*, база — по *pfp-*: применяем к обоим
          (setq *psp-color-mode* *psp-t-pcol*
                *psp-ctb-mono* *psp-t-ctbm*
                *psp-ctb-color* *psp-t-ctbc*)
          (setq *pfp-color-mode* *psp-t-pcol*
                *pfp-ctb-mono* *psp-t-ctbm*
                *pfp-ctb-color* *psp-t-ctbc*)
          (setq n *psp-t-thr*)
          (if (< n 1) (setq n 1))
          (setq *psp-auto-merge-n* n)
          (setcfg "AppData/PlotSPDS/AutoMergeN" (itoa n))
          (setq n *psp-t-delay*)
          (if (< n 0) (setq n 0))
          (setq *psp-open-delay-s* n)
          (setcfg "AppData/PlotSPDS/OpenDelay" (itoa n))
          (setq *psp-open-res* *psp-t-openres*)
          (setcfg "AppData/PlotSPDS/OpenRes" (if *psp-open-res* "1" "0"))
          (setq *psp-del-singles* *psp-t-dels*)
          (setcfg "AppData/PlotSPDS/DelSingles" (if *psp-del-singles* "1" "0"))
          (setq *psp-quality* *psp-t-quality*)
          (setcfg "AppData/PlotSPDS/Quality" (itoa *psp-quality*))
          (setcfg "AppData/PlotFrame/Quality" (itoa *psp-t-pfq*))
          (setq *pfp-quality* *psp-t-pfq*)
          (princ "\nПСП: настройки сохранены. Применено:")
          (princ "\n  +-----------------------------+-----------------------------------+")
          (princ (strcat "\n  | " (psp-pad-right "параметр" 28)
                          "| " (psp-pad-right "значение" 34) "|"))
          (princ "\n  +-----------------------------+-----------------------------------+")
          (defun psp-row (n v)
            (princ (strcat "\n  | " (psp-pad-right n 28)
                           "| " (psp-pad-right (psp-s->str v) 34) "|")))
          (psp-row "папка сохранения"
                   (if (= *psp-pdf-dir* "")
                     "%TEMP%\\PlotFramePDF" *psp-pdf-dir*))
          (psp-row "PDF-принтер (СПДС)" *psp-pc3*)
          (psp-row "цвет печати"
                   (if *psp-color-mode* "цвет" "ч/б"))
          (psp-row "Чёрно-белая печать (CTB)" *psp-ctb-mono*)
          (psp-row "Цветная печать (CTB)" *psp-ctb-color*)
          (psp-row "принтер для A4 (FP)" *psp-t-fpp4*)
          (psp-row "принтер для A3 (FP)" *psp-t-fpp3*)
          (psp-row "автосборка в один PDF"
                   (strcat "при листах > " (itoa *psp-auto-merge-n*)))
          (psp-row "задержка открытия"
                   (strcat (itoa *psp-open-delay-s*) " с"))
          (psp-row "открывать результат"
                   (if *psp-open-res* "да" "нет"))
          (psp-row "удалять одиночные листы"
                   (if *psp-del-singles* "да" "нет"))
          (psp-row "качество СПДС"
                   (nth *psp-quality*
                        (list "Низкое" "Среднее" "Высокое")))
          (psp-row "качество рамки"
                   (nth *psp-t-pfq*
                        (list "Низкое" "Среднее" "Высокое")))
          (princ "\n  +-----------------------------+-----------------------------------+")
          ))))))))
      (unload_dialog d)
      (if (vl-catch-all-error-p res)
        (progn
          (princ (strcat "\nПСП: ошибка диалога настроек [этап: "
                         (psp-s->str st) "]: "))
          (princ (vl-catch-all-error-message res))))
  (princ))

(defun c:ПСПНАСТРОЙКИ () (psp-settings-dialog))
(defun c:PSPSET () (c:ПСПНАСТРОЙКИ))

;; Качество печати SPDS: 0 = формат в формат, 1 = +1, 2 = +2



;; Справка: команды и однократная настройка «тихого» PDF-принтера
(defun c:ПСППОМОЩЬ ( )
  (princ (strcat "\nPlotSPDSToPDF v" *psp-ver* " — экспорт форматов СПДС в PDF."))
  (princ "\nКоманды: ЭКССПДСПДФ (EXPSPDSPDF) — экспорт; ПСПНАСТРОЙКИ (PSPSET) —")
  (princ "\n  настройки (папка PDF, автосборка, задержка, принтер, удаление);")
  (princ "\n  ПСПГС (PSPGS) — путь к Ghostscript;")
  (princ "\n  страховой поиск: <диск>:\\PlotFrameToPDF\\gs\\bin (C:/D:/E:) — портативный gs.")
  (princ "\n  ПСПЭХОВКЛ/ПСПЭХОВЫКЛ — эхо ленты -ПЕЧАТЬ; ПСППОМОЩЬ (PSPHELP) — справка.")
  (princ "\nКачество печати — радиостроки в ПСПНАСТРОЙКИ (СПДС и рамки).")
  (princ "\nПорядок листов: по номеру (15, 15.1, 15.2...), «0» — титульный, первым.")
  (princ "\nБольше трёх листов — сборка в один PDF автоматически;")
  (princ "\n  открывается ТОЛЬКО склейка, одиночные листы не запускаются")
  (princ "\n  и удаляются (повторные попытки ~1 мин — просмотрщик держит файлы).")
  (princ "\nОДНОКРАТНАЯ НАСТРОЙКА «тихого» принтера (если AutoCAD сам")
  (princ "\nоткрывает каждый отпечатанный лист):")
  (princ "\n  1) открыть папку принтеров: в консоли AutoCAD —")
  (princ "\n       (startapp \"explorer.exe\" (getenv \"PrinterConfigDir\"))")
  (princ "\n     (команда ПЛОТТЕРМАНАДЖЕР может не открываться — не страшно)")
  (princ "\n  2) копия DWG To PDF.pc3 -> переименовать в PlotSPDSToPDF.pc3")
  (princ "\n  3) двойной клик по копии -> «Пользовательские свойства...» ->")
  (princ "\n     снять флажок «Показывать результаты в программе просмотра» -> OK")
  (princ "\n  4) в модуле имя уже задано по умолчанию; после загрузки можно")
  (princ "\n     переопределить: (setq *psp-pc3* \"PlotSPDSToPDF.pc3\")")
  (princ "\n  Если копии нет, экспорт падает с «устройство не найдено» — тогда")
  (princ "\n  (setq *psp-pc3* \"DWG To PDF.pc3\") после загрузки.")
  (princ))

(defun c:PSPPOMOSH () (c:ПСППОМОЩЬ))
(defun c:PSPHELP () (c:ПСППОМОЩЬ))




;; Диагностика: показывать/скрывать все подсказки -ПЕЧАТЬ во время
;; серийной печати (эхо команд в консоль)
(defun psp-echo-set (v)
  (setq *psp-plot-echo* v)
  (princ (if v
    "\nПСП: эхо печати ВКЛЮЧЕНО — подсказки -ПЕЧАТЬ будут видны."
    "\nПСП: эхо печати выключено."))
  (princ))
(defun c:ПСПЭХОВКЛ () (psp-echo-set T))
(defun c:ПСПЭХОВЫКЛ () (psp-echo-set nil))
(defun c:PSPECHOON () (psp-echo-set T))
(defun c:PSPECHOOFF () (psp-echo-set nil))

;; Переключение ленты -ПЕЧАТЬ: с ответом на «Масштабировать веса
;; линий?» или без (зависит от сборки AutoCAD)



;; Задать путь к Ghostscript вручную и запомнить его постоянно
(defun c:ПСПГС ( / p)
  (setq p (getstring T
    "\nПолный путь к gswin64c.exe (Enter — очистить): "))
  (if (= p "")
    (progn
      (setq *psp-gs* nil)
      (setcfg "AppData/PlotSPDS/GS" "")
      (princ "\nПСП: путь к Ghostscript очищен, поиск автоматический."))
    (progn
      (setq p (vl-string-trim " \"" p))
      (setq *psp-gs* p)
      (setcfg "AppData/PlotSPDS/GS" p)
      (princ (strcat "\nПСП: Ghostscript: " p
                     "\nПСП: если склейка не соберётся — проверьте путь."))))
  (princ))
(defun c:PSPGS () (c:ПСПГС))
;; ---------------------------------------------------------------------------
;; Загрузка
;; ---------------------------------------------------------------------------

(princ)

;;; -*- coding: windows-1251 -*-
;;; PlotFrameToPDF.lsp
;;;
;;; Экспорт области, выделенной рамкой, в PDF (DWG To PDF.pc3).
;;; Печать через командную строку _.-PLOT с координатами-списками.
;;;
;;; v3.16 относительно v3.10 (база) — только два исправления:
;;; 1) PAPERUPDATE на время печати = 1: подавляет диалог «размер бумаги
;;;    не найден» при первом построении в заново открытом файле
;;;    (сохранение до печати, восстановление на всех выходах).
;;; 2) Лента ответов -ПЕЧАТЬ собирается по вкладке (TILEMODE): наборы
;;;    вопросов Модели и Листа различаются — из-за этого были файлы
;;;    с именем «_N» и оставшийся вопрос «Продолжить построение?».
;;; v3.17: перед -ПЕЧАТЬ активному листу через ActiveX предустанавли-
;;;        ваются устройство и формат (сохранение/восстановление прежних
;;;        значений). Из-за отсутствующего в устройстве формата -ПЕЧАТЬ
;;;        вставляла лишний вопрос Да/Нет — лента съезжала и первая
;;;        печать в файле уходила в PDF с именем по умолчанию.
;;; Загрузка: прямая (load ...) или через единый загрузчик RELOAD
;;; проекта AutoExtraction (раздел плагинов). Маркер редакции для
;;; RELOAD: (ред. 1
;;;
;;; Команды: ЭКСПДФ / EXPPDF / ОЧИСТПДФ / ПФППАПКА / ПФПТЕМП / ПФПЭХОВКЛ

(vl-load-com)

(setq *pfp-ver* "3.27")
;; v3.18: «_As»-ошибка: ответ «_N» (не масштабировать веса линий)
;;        отправлялся безусловно, но ряд сборок (в т.ч. ваша) вопрос
;;        «Масштабировать веса линий?» не задаёт — лента съезжала и
;;        ломалась на «_As» (тонирование). Ответ стал условным
;;        (*pfp-tape-mode*, по умолчанию ВЫКЛ).
;;        Аналогичное решение доказано в PlotSPDSToPDF (ПСПЛЕНТА).
;; T: в ленту -ПЕЧАТЬ добавляется ответ «_N» на вопрос
;; «Масштабировать веса линий?» — ТОЛЬКО для сборок AutoCAD,
;; где такой вопрос задаётся (переменная *pfp-tape-mode*)
(setq *pfp-tape-mode* nil)
;; T: не глушить эхо -ПЕЧАТЬ (диагностика ленты; ПФПЭХОВКЛ/ПФПЭХОВЫКЛ)
(setq *pfp-plot-echo* nil)

(setq *pfp-open-mode* "rundll")
(setq *pfp-open-delay* 300)

(setq *pfp-auto-format*      T)
(setq *pfp-consider-area*    T)
(setq *pfp-size-factor*      2.0)
(setq *pfp-unit-scale*       1.0)
(setq *pfp-max-format*       nil)
(setq *pfp-rotate-invert*    nil)
(setq *pfp-force-orient*     nil)
(setq *pfp-fixed-format*     "ISO_full_bleed_A1_(841.00_x_594.00_MM)")

(setq *pfp-block-size*       50)
(setq *pfp-subdir*           "PlotFramePDF")
(setq *pfp-color-mode*       nil)
(setq *pfp-ctb-mono*         "monochrome.ctb")
(setq *pfp-ctb-color*        "acad.ctb")
(setq *pfp-output-dir*       nil)

;; Сохранённые устройство/формат активного листа (на время печати);
;; заполняется pfp-page-preset, очищается pfp-page-restore
(setq *pfp-page-saved*       nil)

;; ---------------------------------------------------------------------------
;; Таблица форматов
;; (короткое  W_L  H_L  "портрет"  "альбом"  верх_объектов)
;; ---------------------------------------------------------------------------
(setq *pfp-formats*
  '(("A3"   420  297
     "ISO_full_bleed_A3_(297.00_x_420.00_MM)"
     "ISO_full_bleed_A3_(420.00_x_297.00_MM)"
     25)
    ("A2"   594  420
     "ISO_full_bleed_A2_(420.00_x_594.00_MM)"
     "ISO_full_bleed_A2_(594.00_x_420.00_MM)"
     50)
    ("A1"   841  594
     "ISO_full_bleed_A1_(594.00_x_841.00_MM)"
     "ISO_full_bleed_A1_(841.00_x_594.00_MM)"
     100)
    ("A0"  1189  841
     "ISO_full_bleed_A0_(841.00_x_1189.00_MM)"
     "ISO_full_bleed_A0_(841.00_x_1189.00_MM)"
     200)
    ("2A0" 1682 1189
     "ISO_full_bleed_2A0_(1189.00_x_1682.00_MM)"
     "ISO_full_bleed_2A0_(1189.00_x_1682.00_MM)"
     400)
    ("4A0" 2378 1682
     "ISO_full_bleed_4A0_(1682.00_x_2378.00_MM)"
     "ISO_full_bleed_4A0_(1682.00_x_2378.00_MM)"
     999999)))

;; ---------------------------------------------------------------------------
;; Утилиты
;; ---------------------------------------------------------------------------

(defun pfp-get (obj prop)
  (vl-catch-all-apply 'vlax-get-property (list obj prop)))

(defun pfp-safe-put (obj prop val)
  (not (vl-catch-all-error-p
         (vl-catch-all-apply 'vlax-put-property (list obj prop val)))))

;; Предустановка устройства и формата активного листа через ActiveX.
;; Цель: -ПЕЧАТЬ не вставляет лишний вопрос «формат не поддерживается»,
;; из-за которого лента ответов съезжает (первая печать в файле уходила
;; в PDF с именем по умолчанию). Прежние значения запоминаются в
;; *pfp-page-saved* и восстанавливаются pfp-page-restore после печати.
(defun pfp-page-preset (media-name / doc layout cfg med)
  (setq *pfp-page-saved* nil)
  (setq doc (pfp-get (vlax-get-acad-object) 'ActiveDocument))
  (setq layout (pfp-get doc 'ActiveLayout))
  (if (or (null layout) (vl-catch-all-error-p layout))
    nil
    (progn
      (setq cfg (pfp-get layout 'ConfigName)
            med (pfp-get layout 'CanonicalMediaName))
      (setq *pfp-page-saved*
            (list (if (vl-catch-all-error-p cfg) nil cfg)
                  (if (vl-catch-all-error-p med) nil med)))
      (pfp-safe-put layout 'ConfigName "DWG To PDF.pc3")
      (pfp-safe-put layout 'CanonicalMediaName media-name)
      ;; Фактически принявшийся формат (лист/устройство могут от-
      ;; вергнуть имя); лента шлёт имя только если оно подтвердилось.
      (setq med (pfp-get layout 'CanonicalMediaName))
      (if (vl-catch-all-error-p med) nil med))))

;; Восстановление устройства и формата листа после печати.
(defun pfp-page-restore ( / doc layout)
  (if *pfp-page-saved*
    (progn
      (setq doc (pfp-get (vlax-get-acad-object) 'ActiveDocument))
      (setq layout (pfp-get doc 'ActiveLayout))
      (if (and (not (null layout)) (not (vl-catch-all-error-p layout)))
        (progn
          (if (car *pfp-page-saved*)
            (pfp-safe-put layout 'ConfigName (car *pfp-page-saved*)))
          (if (cadr *pfp-page-saved*)
            (pfp-safe-put layout 'CanonicalMediaName
                          (cadr *pfp-page-saved*)))))
      (setq *pfp-page-saved* nil)))
  (princ))

(defun pfp-default-dir ()
  (strcat (getenv "TEMP") "\\" *pfp-subdir*))

(defun pfp-output-dir ( / d )
  (setq d (if *pfp-output-dir* *pfp-output-dir* (pfp-default-dir)))
  (if (not (vl-file-directory-p d)) (vl-mkdir d))
  d)

;; Имя чертежа без расширения (DWGNAME; DWGTITLED — только флаг 0/1)
(defun pfp-drawing-name ( / s k)
  (setq s (getvar "DWGNAME"))
  (if (/= (type s) 'STR) (setq s ""))
  (setq k (strlen s))
  ;; точка трёхсимвольного расширения — на позиции k-3
  (if (and (> k 4) (= (substr s (- k 3) 1) "."))
    (setq s (substr s 1 (- k 4))))
  (if (= s "") (setq s "Рамки"))
  s)

;; Папка чертежа: <папка экспорта>\<имя чертежа> — создаётся при нужде
(defun pfp-drawing-dir ( / d)
  (setq d (strcat (pfp-output-dir) "\\" (pfp-drawing-name)))
  (if (not (vl-file-directory-p d)) (vl-mkdir d))
  d)

(defun pfp-taken-p (dir n)
  (or (findfile (strcat dir "\\" (itoa n) ".pdf"))
      (findfile (strcat dir "\\" (itoa n)))))

(defun pfp-block-free-p (dir start len / i ok)
  (setq i 0 ok T)
  (while (and ok (< i len))
    (if (pfp-taken-p dir (+ start i)) (setq ok nil))
    (setq i (1+ i)))
  ok)

(defun pfp-next-number (dir / n)
  (setq n 1)
  (while (not (pfp-block-free-p dir n *pfp-block-size*))
    (setq n (1+ n)))
  n)

(defun pfp-sleep (ms / old-cmdecho)
  (setq old-cmdecho (getvar "CMDECHO"))
  (setvar "CMDECHO" 0)
  (command "_.delay" ms)
  (setvar "CMDECHO" old-cmdecho))

;; Принудительный сброс зависшего состояния командной строки.
;; Три попытки: Esc через SendCommand, затем пустые Enter, пока CMDACTIVE > 0.
(defun pfp-clear-stuck ( / doc i)
  (setq doc (vl-catch-all-apply 'vla-get-ActiveDocument
                                (list (vlax-get-acad-object))))
  (setq i 0)
  (while (and (< i 5) (> (getvar "CMDACTIVE") 0))
    (vl-catch-all-apply 'vla-SendCommand (list doc (chr 27)))
    (vl-catch-all-apply 'vl-cmdf (list ""))
    (setq i (1+ i)))
  ;; ещё два «холостых» Enter на случай не-CMDACTIVE запросов
  (vl-catch-all-apply 'vl-cmdf (list ""))
  (vl-catch-all-apply 'vl-cmdf (list ""))
  (princ))

;; ---------------------------------------------------------------------------
;; Выбор формата
;; ---------------------------------------------------------------------------

(defun pfp-format-idx (fmt / i lst found)
  (setq i 0 lst *pfp-formats* found nil)
  (while (and lst (not found))
    (if (equal (nth 0 (car lst)) fmt) (setq found i))
    (setq i (1+ i) lst (cdr lst)))
  found)

(defun pfp-format-by-count (n-obj / pair)
  (setq pair *pfp-formats*)
  (while (and (cdr pair) (>= n-obj (nth 5 (car pair))))
    (setq pair (cdr pair)))
  (car pair))

(defun pfp-format-by-area (w-mm h-mm / pair res sz fw fh)
  (setq pair *pfp-formats* res nil)
  (while (and pair (not res))
    (setq sz (car pair)
          fw (* (nth 1 sz) *pfp-size-factor*)
          fh (* (nth 2 sz) *pfp-size-factor*))
    (if (or (and (>= fw w-mm) (>= fh h-mm))
            (and (>= fh w-mm) (>= fw h-mm)))
      (setq res sz))
    (setq pair (cdr pair)))
  (if res res (car (reverse *pfp-formats*))))

(defun pfp-want-landscape (w h)
  (cond
    ((equal *pfp-force-orient* "portrait")  nil)
    ((equal *pfp-force-orient* "landscape") T)
    (t (>= w h))))

(defun pfp-pick-format (n-obj w-mm h-mm / by-cnt by-area idx-cnt idx-area idx cap-idx rec want-land media)
  (if (not *pfp-auto-format*)
    (progn
      (setq want-land (pfp-want-landscape w-mm h-mm))
      (list "fix"
            *pfp-fixed-format*
            (if *pfp-rotate-invert*
              (if want-land "_P" "_L")
              (if want-land "_L" "_P"))))
    (progn
      (setq by-cnt  (pfp-format-by-count n-obj)
            idx-cnt (pfp-format-idx (nth 0 by-cnt))
            idx-area idx-cnt)
      (if *pfp-consider-area*
        (progn
          (setq by-area (pfp-format-by-area w-mm h-mm))
          (if by-area (setq idx-area (pfp-format-idx (nth 0 by-area))))))
      (setq idx (max idx-cnt idx-area))
      ;; Качество: Низкое = формат меньше, Отличное = формат больше
      (setq idx (+ idx (cond ((= *pfp-quality* 0) -1)
                             ((= *pfp-quality* 2) 1)
                             (t 0))))
      (if (>= idx (length *pfp-formats*))
        (setq idx (1- (length *pfp-formats*))))
      (if *pfp-max-format*
        (progn
          (setq cap-idx (pfp-format-idx *pfp-max-format*))
          (if (and cap-idx (> idx cap-idx)) (setq idx cap-idx))))
      (if (< idx 0)
        ;; Низкое при авто=A3: A4 в таблице нет — отдельная запись
        (setq rec (list "A4" 297 210
                        "ISO_full_bleed_A4_(210.00_x_297.00_MM)"
                        "ISO_full_bleed_A4_(297.00_x_210.00_MM)"
                        0))
        (setq rec (nth idx *pfp-formats*)))
      (setq want-land (pfp-want-landscape w-mm h-mm)
            media (if want-land (nth 4 rec) (nth 3 rec)))
      (list (nth 0 rec)
            media
            (if *pfp-rotate-invert*
              (if want-land "_P" "_L")
              (if want-land "_L" "_P"))))))

;; ---------------------------------------------------------------------------
;; Открытие PDF
;; ---------------------------------------------------------------------------

(defun pfp-open-rundll (path / args)
  (setq args (strcat "url.dll,FileProtocolHandler \"" path "\""))
  (startapp "rundll32.exe" args))

(defun pfp-open-shell (path / sh)
  (setq sh (vl-catch-all-apply 'vlax-create-object (list "WScript.Shell")))
  (if (and sh (not (vl-catch-all-error-p sh)))
    (progn
      (vl-catch-all-apply
        'vlax-invoke-method
        (list sh 'Run (strcat "\"" path "\"") 1 :vlax-false))
      (vl-catch-all-apply 'vlax-release-object (list sh)))
    (startapp "explorer.exe" path)))

(defun pfp-open-explorer (path) (startapp "explorer.exe" path))

(defun pfp-open (path)
  (cond
    ((= *pfp-open-mode* "shell")    (pfp-open-shell    path))
    ((= *pfp-open-mode* "explorer") (pfp-open-explorer path))
    (t                              (pfp-open-rundll   path))))

;; ---------------------------------------------------------------------------
;; Диалог выбора папки
;; ---------------------------------------------------------------------------

(defun pfp-browse-folder ( / shell folder self path)
  (setq shell (vl-catch-all-apply 'vlax-create-object (list "Shell.Application")))
  (if (or (null shell) (vl-catch-all-error-p shell))
    nil
    (progn
      (setq folder
            (vl-catch-all-apply
              'vlax-invoke-method
              (list shell 'BrowseForFolder 0
                    "Выберите папку для экспорта PDF" 1)))
      (vl-catch-all-apply 'vlax-release-object (list shell))
      (if (or (null folder) (vl-catch-all-error-p folder))
        nil
        (progn
          (setq self (pfp-get folder 'Self)
                path (if self (pfp-get self 'Path) nil))
          (vl-catch-all-apply 'vlax-release-object (list folder))
          (if (or (null path) (vl-catch-all-error-p path)) nil path))))))

;; ---------------------------------------------------------------------------
;; Форматирование
;; ---------------------------------------------------------------------------

(defun pfp-pad-left (s width / n)
  (setq n (- width (strlen s)))
  (while (> n 0) (setq s (strcat " " s) n (1- n))) s)

(defun pfp-pad-right (s width / n)
  (setq n (- width (strlen s)))
  (while (> n 0) (setq s (strcat s " ") n (1- n))) s)

(defun pfp-mode-str () (if *pfp-color-mode* "цветная" "ч/б"))

;; ---------------------------------------------------------------------------
;; Справки
;; ---------------------------------------------------------------------------

(defun pfp-print-table ( / pair prev thr short line w h wstr eff)
  (princ "\nТаблица форматов:")
  (princ "\nКритерий выбора — МАКСИМУМ из двух: количество объектов ИЛИ габариты рамки.")
  (princ (strcat "\n(в критерии по габаритам размеры формата умножаются на "
                 (rtos *pfp-size-factor* 2 2) ")"))
  (princ
    (strcat "\n  " (pfp-pad-left "формат" 8)
            "  " (pfp-pad-left "размер (мм)" 16)
            "  " (pfp-pad-left "объектов" 12)
            "  " "рамка вписывается до"))
  (princ
    (strcat "\n  " (pfp-pad-left "------" 8)
            "  " (pfp-pad-left "-----------" 16)
            "  " (pfp-pad-left "----------" 12)
            "  " "--------------------"))
  (setq pair *pfp-formats* prev 0)
  (foreach rec pair
    (setq short (nth 0 rec) w (nth 1 rec) h (nth 2 rec) thr (nth 5 rec)
          wstr  (strcat (itoa w) " x " (itoa h) " мм")
          eff   (strcat (itoa (fix (* w *pfp-size-factor*))) " x "
                        (itoa (fix (* h *pfp-size-factor*))) " мм")
          line  (strcat (itoa prev) ".."
                        (if (>= thr 999999) "..." (itoa (1- thr)))))
    (princ (strcat "\n  " (pfp-pad-left short 8)
                   "  " (pfp-pad-left wstr 16)
                   "  " (pfp-pad-left line 12)
                   "  " "до " eff))
    (setq prev thr))
  (princ))

(defun pfp-row (left right)
  (princ (strcat "\n  " (pfp-pad-right left 36) "  " right)))

(defun pfp-print-vars ( / dir-str max-str area-str orient-str)
  (setq dir-str    (if *pfp-output-dir* *pfp-output-dir* "nil (= %TEMP%\\PlotFramePDF)")
        max-str    (if *pfp-max-format* *pfp-max-format* "nil (без ограничения)")
        area-str   (if *pfp-consider-area* "T (учитывать)" "nil (только объекты)")
        orient-str (if *pfp-force-orient* *pfp-force-orient* "nil (авто)"))
  (princ "\nПеременные модуля:")
  (pfp-row "переменная" "назначение / текущее значение")
  (pfp-row "--------------------" "--------------------------------------------------------------")
  (pfp-row "*pfp-color-mode*"       (strcat "nil = ч/б, T = цвет  ["
                                            (if *pfp-color-mode* "T" "nil") "]"))
  (pfp-row "*pfp-ctb-mono*"         (strcat "CTB для ч/б  [" *pfp-ctb-mono* "]"))
  (pfp-row "*pfp-ctb-color*"        (strcat "CTB для цвета  [" *pfp-ctb-color* "]"))
  (pfp-row "*pfp-output-dir*"       (strcat "папка экспорта  [" dir-str "]"))
  (pfp-row "*pfp-consider-area*"    (strcat "учёт габаритов  [" area-str "]"))
  (pfp-row "*pfp-size-factor*"      (strcat "множитель  [" (rtos *pfp-size-factor* 2 2) "]"))
  (pfp-row "*pfp-quality*"          (strcat "качество  ["
                                            (cond ((= *pfp-quality* 0) "Низкое (авто -1)")
                                                  ((= *pfp-quality* 2) "Высокое (авто +1)")
                                                  (t "Среднее (авто)")) "]"))
  (pfp-row "*pfp-unit-scale*"       (strcat "мм в ед.  [" (rtos *pfp-unit-scale* 2 3) "]"))
  (pfp-row "*pfp-max-format*"       (strcat "макс. формат  [" max-str "]"))
  (pfp-row "*pfp-force-orient*"     (strcat "форс ориент.  [" orient-str "]"))
  (pfp-row "*pfp-open-delay*"       (strcat "задержка  [" (itoa *pfp-open-delay*) "]"))
  (pfp-row "*pfp-open-mode*"        (strcat "способ откр.  [" *pfp-open-mode* "]"))
  (pfp-row "*pfp-block-size*"       (strcat "блок номеров  [" (itoa *pfp-block-size*) "]"))
  (pfp-row "*pfp-subdir*"           (strcat "подпапка  [" *pfp-subdir* "]"))
  (princ))

(defun pfp-print-examples ()
  (princ "\nПримеры настройки:")
  (pfp-row "действие" "команда")
  (pfp-row "------------------------------------"
           "--------------------------------------------------------------")
  (pfp-row "включить цвет"           "(setq *pfp-color-mode* T)")
  (pfp-row "вернуть ч/б"             "(setq *pfp-color-mode* nil)")
  (pfp-row "своя папка экспорта"
           "(setq *pfp-output-dir* \"D:/Yandex.Disk/Документы/Файлы PDF\")")
  (pfp-row "чертёж в метрах"         "(setq *pfp-unit-scale* 1000.0)")
  (pfp-row "множитель 1.0"           "(setq *pfp-size-factor* 1.0)")
  (pfp-row "множитель 2.0"           "(setq *pfp-size-factor* 2.0)")
  (pfp-row "ограничить A0"           "(setq *pfp-max-format* \"A0\")")
  (pfp-row "только по объектам"      "(setq *pfp-consider-area* nil)")
  (pfp-row "форс альбомной"          "(setq *pfp-force-orient* \"landscape\")")
  (pfp-row "форс портретной"         "(setq *pfp-force-orient* \"portrait\")")
  (pfp-row "снять форс"              "(setq *pfp-force-orient* nil)")
  (pfp-row "задержка 500 мс"         "(setq *pfp-open-delay* 500)")
  (princ))

(defun pfp-print-hints ()
  (princ "\nDWG To PDF.pc3 — ускорение (один раз):")
  (princ "\n  Диспетчер плоттеров -> изменить DWG To PDF.pc3 -> Свойства -> Custom Properties")
  (princ "\n    Raster graphics resolution : 150..200 dpi")
  (princ "\n    Vector graphics resolution : 1200 dpi")
  (princ)
  (princ "\nПеред печатью автоматически сбрасывается зависшее состояние командной строки.")
  (princ "\nСписок media name — команда ПФПМЕДИА.")
  (princ))

(defun pfp-print-settings ()
  (princ "\nТекущие настройки:")
  (princ (strcat "\n  режим печати : " (pfp-mode-str)
                 " (" (if *pfp-color-mode* *pfp-ctb-color* *pfp-ctb-mono*) ")"))
  (princ (strcat "\n  папка        : " (if *pfp-output-dir*
                                         *pfp-output-dir* (pfp-default-dir))))
  (princ (strcat "\n  учёт площади : " (if *pfp-consider-area* "да" "нет")))
  (princ (strcat "\n  множитель    : " (rtos *pfp-size-factor* 2 2)))
  (princ (strcat "\n  масштаб ед.  : " (rtos *pfp-unit-scale* 2 3) " мм"))
  (princ (strcat "\n  макс. формат : " (if *pfp-max-format* *pfp-max-format* "нет")))
  (princ (strcat "\n  форс ориент. : " (if *pfp-force-orient* *pfp-force-orient* "нет")))
  (princ (strcat "\n  задержка     : " (itoa *pfp-open-delay*) " мс"))
  (princ (strcat "\n  способ откр. : " *pfp-open-mode*))
  (princ))

;; ---------------------------------------------------------------------------
;; Список media name
;; ---------------------------------------------------------------------------

(defun pfp-list-media ( / acad doc layout lst v)
  (setq acad   (vlax-get-acad-object))
  (setq doc    (pfp-get acad 'ActiveDocument))
  (setq layout (pfp-get doc  'ActiveLayout))
  (if (or (null layout) (vl-catch-all-error-p layout))
    nil
    (progn
      (setq lst (vl-catch-all-apply 'vlax-invoke-method
                                    (list layout 'GetCanonicalMediaNames)))
      (if (vl-catch-all-error-p lst) (setq lst nil))
      (if lst (setq v (vl-catch-all-apply 'vlax-variant-value (list lst))))
      (if (and v (not (vl-catch-all-error-p v))) (setq lst v))
      (if (and lst (not (listp lst)))
        (setq lst (vl-catch-all-apply 'vlax-safearray->list (list lst))))
      (if (vl-catch-all-error-p lst) (setq lst nil))
      lst)))



;; ---------------------------------------------------------------------------
;; Основная процедура — печать через -PLOT
;; ---------------------------------------------------------------------------

(defun plot-frame-to-pdf-run ( / pt1 pt2 x1 y1 x2 y2 w h w-mm h-mm
                                   dir fname fname-pdf
                                   fmt media-name short-name orient-str rot-str
                                   n-obj ss-filter ctb-name
                                   old-trans has-trans old-bg old-paper
                                   plot-tape old-cmdecho chk
                                   attempt pdf-found plot-err )

  (setq has-trans
        (not (vl-catch-all-error-p
               (vl-catch-all-apply 'getvar '("PLOTTRANSPARENCYOVERRIDE")))))
  (if has-trans (setq old-trans (getvar "PLOTTRANSPARENCYOVERRIDE")))
  (setq old-bg      (getvar "BACKGROUNDPLOT"))
  ;; PAPERUPDATE: сохраняем, печатаем с 1 (без диалога «размер бумаги
  ;; не найден»), восстанавливаем на всех выходах (см. ниже)
  (setq old-paper   (vl-catch-all-apply 'getvar (list "PAPERUPDATE")))
  ;; Качество (реестр, ПСПНАСТРОЙКИ): сдвиг формата от авто-выбора:
  ;; Низкое = формат меньше, Среднее = как всегда, Отличное = больше
  (setq s-q (getcfg "AppData/PlotFrame/Quality"))
  (if (= (type s-q) 'STR)
    (progn
      (setq s-q (atoi s-q))
      (if (and (>= s-q 0) (<= s-q 2)) (setq *pfp-quality* s-q))))
  ;; Общая папка сохранения (ПСПНАСТРОЙКИ): непустая -> печатаем туда
  (setq s-o (getcfg "AppData/PlotFrame/OutDir"))
  (if (= (type s-o) 'STR)
    (setq *pfp-output-dir* (if (/= s-o "") s-o nil)))
  ;; Цвет и CTB из ПСПНАСТРОЙКИ (задача 12)
  (setq s-o (getcfg "AppData/PlotFrame/ColorMode"))
  (if (= (type s-o) 'STR) (setq *pfp-color-mode* (= s-o "1")))
  (setq s-o (getcfg "AppData/PlotFrame/CtbMono"))
  (if (and (= (type s-o) 'STR) (/= s-o "")) (setq *pfp-ctb-mono* s-o))
  (setq s-o (getcfg "AppData/PlotFrame/CtbColor"))
  (if (and (= (type s-o) 'STR) (/= s-o "")) (setq *pfp-ctb-color* s-o))
  (setq old-cmdecho (getvar "CMDECHO"))

  ;; Сброс возможного «хвоста» от предыдущих команд
  (pfp-clear-stuck)

  (setvar "BACKGROUNDPLOT" 0)
  (if (not (vl-catch-all-error-p old-paper)) (setvar "PAPERUPDATE" 1))
  (if has-trans (setvar "PLOTTRANSPARENCYOVERRIDE" 1))

  (princ "\nЭкспорт области в PDF. Укажите рамку выделения.")
  (setq pt1 (getpoint "\nПервый угол рамки: "))
  (cond
    ((null pt1) (princ "\nОтменено.")
                (setvar "BACKGROUNDPLOT" old-bg)
                (if (not (vl-catch-all-error-p old-paper))
                  (setvar "PAPERUPDATE" old-paper))
                (if has-trans (setvar "PLOTTRANSPARENCYOVERRIDE" old-trans)))
    (t
      (setq pt2 (getcorner pt1 "\nВторой угол рамки: "))
      (cond
        ((null pt2) (princ "\nОтменено.")
                    (setvar "BACKGROUNDPLOT" old-bg)
                    (if (not (vl-catch-all-error-p old-paper))
                      (setvar "PAPERUPDATE" old-paper))
                    (if has-trans (setvar "PLOTTRANSPARENCYOVERRIDE" old-trans)))
        (t
          (setq x1 (min (car  pt1) (car  pt2))
                y1 (min (cadr pt1) (cadr pt2))
                x2 (max (car  pt1) (car  pt2))
                y2 (max (cadr pt1) (cadr pt2))
                w  (- x2 x1) h (- y2 y1)
                w-mm (* w *pfp-unit-scale*)
                h-mm (* h *pfp-unit-scale*))

          (setq orient-str (if (pfp-want-landscape w h) "альбомный" "портретный"))

          (setq ss-filter (ssget "_C" (list x1 y1) (list x2 y2)))
          (setq n-obj (if ss-filter (sslength ss-filter) 0))

          (setq fmt        (pfp-pick-format n-obj w-mm h-mm)
                short-name (nth 0 fmt)
                media-name (nth 1 fmt)
                rot-str    (nth 2 fmt))

          (setq ctb-name (if *pfp-color-mode* *pfp-ctb-color* *pfp-ctb-mono*))

          (setq dir       (pfp-drawing-dir)
                fname     (itoa (pfp-next-number dir))
                fname-pdf (strcat dir "\\" fname))

          ;; Предустановка формата: убирает лишний вопрос -ПЕЧАТЬ
          ;; на первой печати в файле (см. pfp-page-preset)
          ;; Печать через -ПЛОТ, до двух попыток. Наборы вопросов
          ;; Модели и Листа РАЗЛИЧАЮТСЯ; лента собирается по TILEMODE,
          ;; иначе ответы «съезжают». В ленте недопустимы nil и про-
          ;; пуски: каждый ответ — на свой вопрос (инцидент 3.22–3.23:
          ;; выпала строка устройства). На Листе формат — всегда
          ;; «Enter» (он уже предустановлен, лист хранит портретный
          ;; канон); на Модели — факт предустановки (chk).
          (setq attempt 0 pdf-found nil)
          (while (and (< attempt 2) (not pdf-found))
            (setq attempt (1+ attempt))
            (setq chk (pfp-page-preset media-name))
            (setvar "CMDECHO" (if *pfp-plot-echo* 1 0))
            (setq plot-tape
              (append
                (list "_.-plot"
                      "_Y"                 ; подробная настройка
                      ""                   ; текущий лист
                      "DWG To PDF.pc3"     ; устройство
                      (cond                ; формат: nil недопустим
                        ((= 1 (getvar "TILEMODE")) "") ;Лист: Enter
                        ((= (type chk) 'STR) chk) ;факт предустановки
                        (t media-name))
                      "_M"                 ; мм
                      rot-str              ; ориентация _L / _P
                      "_N"                 ; не переворачивать
                      "_W"                 ; область: Рамка
                      (list x1 y1)         ; нижний левый угол
                      (list x2 y2)         ; верхний правый угол
                      "_F"                 ; вписать
                      "_C"                 ; центрировать
                      "_Y"                 ; учитывать стили печати
                      ctb-name             ; CTB-файл
                      "_Y")                ; учитывать веса линий
                (if (= 1 (getvar "TILEMODE"))
                  ;; --- вкладка Модель ---
                  (append
                    (if *pfp-tape-mode*    ; «Масштабировать веса?» задаёт
                      (list "_N"))         ; не каждая сборка
                    (list
                      "_As"                ; тонирование: по отображению
                      fname-pdf            ; имя файла
                      "_N"                 ; не сохранять в параметры
                      "_Y"))               ; печатать
                  ;; --- вкладка Лист ---
                  ;; Три «Нет» (масштабировать веса / печатать лист
                  ;; первым / скрывать объекты листа); «записать изме-
                  ;; нения в макет» спрашивается не всегда (зависит от
                  ;; состояния листа) — её закрывает вторая попытка
                  ;; с четвёртым «Нет». После имени: не сохранять,
                  ;; печатать.
                  (append
                    (list "_N" "_N" "_N")
                    (if (= attempt 2) (list "_N"))
                    (list fname-pdf "_N" "_Y")))))
            (setq plot-err
                  (vl-catch-all-apply 'apply (list 'command plot-tape)))
            (setvar "CMDECHO" old-cmdecho)
            ;; Дождаться полного завершения -PLOT
            (while (> (getvar "CMDACTIVE") 0) (command))
            (pfp-page-restore)
            (if (findfile (strcat fname-pdf ".pdf"))
              (setq pdf-found T)
              (if (< attempt 2)
                (progn
                  (if (vl-catch-all-error-p plot-err)
                    (princ "\nПФП: лента печати сорвалась — вторая попытка (плюс «Нет» на «записать изменения»).")
                    (princ "\nПФП: PDF не появился — повторная попытка..."))
                  (pfp-clear-stuck)))))

          (if has-trans (setvar "PLOTTRANSPARENCYOVERRIDE" old-trans))
          (setvar "BACKGROUNDPLOT" old-bg)
          (if (not (vl-catch-all-error-p old-paper))
            (setvar "PAPERUPDATE" old-paper))

          (setq fname-pdf
                (cond ((findfile (strcat fname-pdf ".pdf"))
                       (strcat fname-pdf ".pdf"))
                      ((findfile fname-pdf) fname-pdf)
                      (t nil)))

          (if fname-pdf
            (progn
              (princ (strcat "\nPDF создан: " fname-pdf
                             " ||| объектов: " (itoa n-obj)
                             " ||| площадь рамки: "
                             (rtos w-mm 2 0) "x" (rtos h-mm 2 0) " мм"
                             " ||| формат: " short-name " " orient-str
                             " ||| область: Рамка"
                             " ||| печать: " (pfp-mode-str)
                             " ||| задержка: " (itoa *pfp-open-delay*) " мс"))
              (princ (strcat "\n  media name: " media-name))
              (pfp-sleep *pfp-open-delay*)
              (pfp-open fname-pdf))
            (princ "\nНе удалось создать PDF (файл не найден после -PLOT)."))
          (princ))))))

;; ---------------------------------------------------------------------------
;; Очистка
;; ---------------------------------------------------------------------------

(defun plot-frame-to-pdf-clean ( / dir files cnt)
  (setq dir (pfp-drawing-dir))
  (if (not (vl-file-directory-p dir))
    (princ "\nПапка не существует.")
    (progn
      (setq files (vl-directory-files dir "*.pdf" 1) cnt 0)
      (foreach f files
        (if (vl-file-delete (strcat dir "\\" f))
          (setq cnt (1+ cnt))))
      (princ (strcat "\nУдалено PDF: " (itoa cnt) " в " dir)))))

;; ---------------------------------------------------------------------------
;; Команды
;; ---------------------------------------------------------------------------

(defun c:ЭКСПДФ  () (plot-frame-to-pdf-run))
(defun c:EXPPDF  () (plot-frame-to-pdf-run))
(defun c:ОЧИСТПДФ () (plot-frame-to-pdf-clean))







(defun c:ПФППАПКА ( / p)
  (setq p (pfp-browse-folder))
  (if p (progn (setq *pfp-output-dir* p)
               (princ (strcat "\nПФП: папка — " p)))
      (princ "\nПФП: выбор отменён."))
  (princ))

(defun c:ПФПЭХОВКЛ () (setq *pfp-plot-echo* T)
  (princ "\nПФП: эхо печати ВКЛЮЧЕНО — подсказки -ПЕЧАТЬ будут видны.")(princ))
(defun c:PFPECHOON () (c:ПФПЭХОВКЛ))
(defun c:ПФПЭХОВЫКЛ () (setq *pfp-plot-echo* nil)
  (princ "\nПФП: эхо печати выключено.")(princ))
(defun c:PFPECHOOFF () (c:ПФПЭХОВЫКЛ))


(defun c:ПФПТЕМП ()
  (setq *pfp-output-dir* nil)
  (princ (strcat "\nПФП: папка — " (pfp-default-dir)))
  (princ))

;; ---------------------------------------------------------------------------
;; Автозагрузка
;; ---------------------------------------------------------------------------
(princ)

;;; PlotFrameToFP.lsp — печать рамки чертежа на системный принтер
;;; (FinePrint и любой другой, заданный в ПСПНАСТРОЙКИ).
;;; v1.02 — ленты Модель/Лист сняты с эхо-логов (Enter у «Сохранить»).
;;; Команды: ЭКСФПА4 / EXPFPA4 — участок чертежа на A4,
;;;          ЭКСФПА3 / EXPFPA3 — участок чертежа на A3.
;;; Ориентация распознаётся по рамке (альбом/портрет). Формат
;;; ФИКСИРОВАННЫЙ и СТАНДАРТНЫЙ (A4/A3, с полями принтера), масштаб
;;; «Вписать», по центру. Цвет и CTB — общие с базой и СПДС
;;; (ПСПНАСТРОЙКИ -> AppData/PlotFrame). Принтеры для A4 и A3 —
;;; свои, задаются в ПСПНАСТРОЙКИ, умолчание FinePrint.
;;; Печать лентами -ПЕЧАТЬ: формат предустанавливается через ActiveX
;;; (разрешённое исключение) и в ленту не посылается; вопрос «Запи-
;;; сать изменения в макет?» непостоянен — сбой ленты перехватывает-
;;; ся, выполняется вторая попытка с «Нет» в хвосте. Результат НЕ
;;; открывается и не удаляется — FinePrint показывает своё окно.

;; v1.03: баннер печатает фактическую версию файла (в 1.01/1.02
;;        строку баннера забыл обновить — печаталось «v1.00»).
;; v1.02: хвосты лент приведены к фактическим (эхо-логи 1.01):
;;        Модель: _As -> в-файл _N -> сохранить (Enter=Н) -> перей-
;;        ти _Y; Лист: веса _N -> первыми _N -> скрыть _N -> в-файл
;;        _N -> сохранить (Enter) -> перейти _Y. Enter у «Сохранить»
;;        страхует отсутствие вопроса. «Масштабировать веса» на Лис-
;;        те — всегда Н (ФПЛЕНТА больше не влияет).
;; v1.01: системный принтер опрашивается иначе, чем PDF: имени
;; файла НЕТ, вместо него «Запись чертежа в файл? <Н>» (ответ Н);
;; «Сохранить изменения параметров листа?» непостоянен — закрыва-
;; ется второй попыткой. fp-cfg: пустое значение = умолчание
;; (getcfg отсутствующего ключа возвращает "" — из-за этого бана-
;; нер печатал «принтер: » без имени).
;; T: слать «Нет» на «Масштабировать веса линий?» (не каждая сборка
;; задаёт этот вопрос (переменная *fp-tape-mode*)
(setq *fp-tape-mode* nil)
;; T: не глушить эхо -ПЕЧАТЬ (диагностика; ФПЭХОВКЛ / ФПЭХОВЫКЛ)
(setq *fp-plot-echo* nil)

;; Значение реестра настроек или умолчание (пустая строка — тоже
;; «нет значения»: getcfg отсутствующего ключа даёт "")
(defun fp-cfg (key def / s)
  (setq s (getcfg key))
  (if (and (= (type s) 'STR) (/= s "")) s def))

(defun fp-s->str (x)
  (cond
    ((= (type x) 'STR) x)
    ((null x) "")
    (t (vl-princ-to-string x))))

;; Сброс зависшей -ПЕЧАТЬ (Ctrl+C через SendCommand, без Enter)
(defun fp-clear-stuck ( / doc i)
  (setq doc (vl-catch-all-apply 'vla-get-ActiveDocument
                                (list (vlax-get-acad-object))))
  (setq i 0)
  (while (and (< i 5) (> (getvar "CMDACTIVE") 0))
    (vl-catch-all-apply 'vla-SendCommand (list doc (chr 27)))
    (setq i (1+ i)))
  (princ))

;; ActiveX-обёртки (только предустановка/восстановление листа —
;; разрешённое исключение перед -ПЕЧАТЬ)
(defun fp-get (obj prop)
  (vl-catch-all-apply 'vlax-get-property (list obj prop)))

(defun fp-safe-put (obj prop val)
  (not (vl-catch-all-error-p
         (vl-catch-all-apply 'vlax-put-property (list obj prop val)))))

;; Предустановка принтера и формата активного листа; прежние
;; значения -> *fp-page-saved* -> fp-page-restore
(defun fp-page-preset (printer fmt / doc layout cfg med)
  (setq *fp-page-saved* nil)
  (setq doc (fp-get (vlax-get-acad-object) 'ActiveDocument))
  (setq layout (fp-get doc 'ActiveLayout))
  (if (or (null layout) (vl-catch-all-error-p layout))
    nil
    (progn
      (setq cfg (fp-get layout 'ConfigName)
            med (fp-get layout 'CanonicalMediaName))
      (setq *fp-page-saved*
            (list (if (vl-catch-all-error-p cfg) nil cfg)
                  (if (vl-catch-all-error-p med) nil med)))
      (fp-safe-put layout 'ConfigName printer)
      (fp-safe-put layout 'CanonicalMediaName fmt))))

(defun fp-page-restore ( / doc layout)
  (if *fp-page-saved*
    (progn
      (setq doc (fp-get (vlax-get-acad-object) 'ActiveDocument))
      (setq layout (fp-get doc 'ActiveLayout))
      (if (and (not (null layout)) (not (vl-catch-all-error-p layout)))
        (progn
          (if (car *fp-page-saved*)
            (fp-safe-put layout 'ConfigName (car *fp-page-saved*)))
          (if (cadr *fp-page-saved*)
            (fp-safe-put layout 'CanonicalMediaName
                         (cadr *fp-page-saved*)))))
      (setq *fp-page-saved* nil)))
  (princ))

;; Основная процедура: рамка -> принтер, формат fmt ("A4"/"A3")
(defun fp-run (fmt / pt1 pt2 x1 y1 x2 y2 w h rot ctb printer
                  old-bg old-paper old-cmdecho attempt tape res fail)
  (setq ctb (if (= (fp-cfg "AppData/PlotFrame/ColorMode" "0") "1")
              (fp-cfg "AppData/PlotFrame/CtbColor" "acad.ctb")
              (fp-cfg "AppData/PlotFrame/CtbMono" "monochrome.ctb")))
  (setq printer (fp-cfg (strcat "AppData/PlotFrame/FPPrinter" fmt)
                        "FinePrint"))
  (setq old-bg      (getvar "BACKGROUNDPLOT"))
  (setq old-paper   (vl-catch-all-apply 'getvar (list "PAPERUPDATE")))
  (setq old-cmdecho (getvar "CMDECHO"))
  (fp-clear-stuck)
  (setvar "BACKGROUNDPLOT" 0)
  (if (not (vl-catch-all-error-p old-paper)) (setvar "PAPERUPDATE" 1))
  (princ (strcat "\nЭкспорт рамки на " fmt " (принтер: " printer
                 "). Укажите рамку выделения."))
  (setq pt1 (getpoint "\nПервый угол рамки: "))
  (cond
    ((null pt1)
     (princ "\nОтменено.")
     (setvar "BACKGROUNDPLOT" old-bg)
     (if (not (vl-catch-all-error-p old-paper))
       (setvar "PAPERUPDATE" old-paper)))
    (t
     (setq pt2 (getcorner pt1 "\nВторой угол рамки: "))
     (cond
       ((null pt2)
        (princ "\nОтменено.")
        (setvar "BACKGROUNDPLOT" old-bg)
        (if (not (vl-catch-all-error-p old-paper))
          (setvar "PAPERUPDATE" old-paper)))
       (t
        (setq x1 (min (car pt1) (car pt2))
              y1 (min (cadr pt1) (cadr pt2))
              x2 (max (car pt1) (car pt2))
              y2 (max (cadr pt1) (cadr pt2))
              w  (- x2 x1)
              h  (- y2 y1))
        (setq rot (if (>= w h) "_L" "_P"))
        ;; До двух попыток: «Записать изменения в макет?» задаётся
        ;; не всегда; сбой ленты -> вторая попытка с «Нет» в хвосте
        (setq attempt 0 fail nil)
        (while (< attempt 2)
          (setq attempt (1+ attempt))
          (fp-page-preset printer fmt)
          (setvar "CMDECHO" (if *fp-plot-echo* 1 0))
          (setq tape
            (append
              (list "_.-plot"
                    "_Y"                   ; подробная настройка
                    ""                     ; текущий лист
                    printer                ; системный принтер
                    ""                     ; формат уже предустановлен
                    "_M"                   ; мм
                    rot                    ; ориентация по рамке
                    "_N"                   ; не переворачивать
                    "_W"                   ; область: Рамка
                    (list x1 y1)           ; нижний левый угол
                    (list x2 y2)           ; верхний правый угол
                    "_F"                   ; вписать
                    "_C"                   ; центрировать
                    "_Y"                   ; учитывать стили печати
                    ctb                    ; CTB (общий с базой/СПДС)
                    "_Y")                  ; учитывать веса линий
              ;; Ленты сняты с эхо-логов 1.01 (Модель и Лист).
              ;; Модель: тонирование (_As) -> «Запись чертежа в файл?»
              ;; (_N) -> «Сохранить изменения параметров листа?»
              ;; (Enter = Н) -> «Перейти к печати?» (_Y = Д). Enter
              ;; вместо Н у «Сохранить» делает ленту устойчивой: если
              ;; вопроса нет, Enter уходит в «Перейти» и даёт Д.
              (if (= 1 (getvar "TILEMODE"))
                (list "_As" "_N" "" "_Y")
                ;; Лист: «Масштабировать веса?» (Н, спрашивает всегда)
                ;; -> «Печатать объекты листа первыми?» (Н) -> «Скрывать
                ;; объекты листа?» (Н) -> «Запись чертежа в файл?» (Н)
                ;; -> «Сохранить изменения» (Enter) -> «Перейти» (_Y)
                (list "_N" "_N" "_N" "_N" "" "_Y"))))
          (setq res (vl-catch-all-apply 'apply (list 'command tape)))
          (setvar "CMDECHO" old-cmdecho)
          (fp-page-restore)
          (cond
            ((vl-catch-all-error-p res)
             (fp-clear-stuck)
             (setq fail T)
             (if (< attempt 2)
               (princ "\nФП: лента сорвалась — вторая попытка.")))
            ((> (getvar "CMDACTIVE") 0)
             (fp-clear-stuck)
             (setq fail T)
             (if (< attempt 2)
               (princ "\nФП: -ПЕЧАТЬ ждёт ответа — вторая попытка.")))
            (t (setq fail nil attempt 2))))
        (if fail
          (princ "\nФП: отправить не удалось — включите ФПЭХОВКЛ и повторите.")
          (princ (strcat "\nФП: отправлено на печать (" fmt
                         " -> " printer ").")))
        (setvar "BACKGROUNDPLOT" old-bg)
        (if (not (vl-catch-all-error-p old-paper))
          (setvar "PAPERUPDATE" old-paper))))))
  (princ))

;; Эхо ленты -ПЕЧАТЬ (диагностика)
(defun fp-echo-set (v)
  (setq *fp-plot-echo* v)
  (princ (if v
    "\nФП: эхо печати ВКЛЮЧЕНО — подсказки -ПЕЧАТЬ будут видны."
    "\nФП: эхо печати выключено."))
  (princ))
(defun c:ФПЭХОВКЛ () (fp-echo-set T))
(defun c:ФПЭХОВЫКЛ () (fp-echo-set nil))
(defun c:FPECHOON () (c:ФПЭХОВКЛ))
(defun c:FPECHOOFF () (c:ФПЭХОВЫКЛ))

;; «Масштабировать веса?» на Листе отвечается всегда (Н)



;; Команды
(defun c:ЭКСФПА4 () (fp-run "A4"))
(defun c:ЭКСФПА3 () (fp-run "A3"))
(defun c:EXPFPA4 () (c:ЭКСФПА4))
(defun c:EXPFPA3 () (c:ЭКСФПА3))

(princ)
(princ)


;;; ============================================================
;;; секция 4: ЭКССПДСФП (фаза 2) — форматы СПДС на СИСТЕМНЫЙ
;;; принтер. Формат РАМКИ СПДС решает, куда печатать:
;;;   A4          -> «Принтер A4» (ПСПНАСТРОЙКИ), бумага A4
;;;   A3 и выше   -> «Принтер A3» (ПСПНАСТРОЙКИ), бумага A3
;;; Ориентация — как у рамки; масштаб — всегда «Вписать»
;;; (A4/A3 печатаются вписанными в бумагу, крупные ужимаются).
;;; Кратность рамки (A4X2/A4X3) поднимает формат по шагам
;;; (A4X2 -> A3). Ничего не сохраняется/не склеивается/не
;;; открывается/не удаляется — бумага выходит из принтера.
;;; Диагностика: общие ФПЭХОВКЛ / ФПЭХОВЫКЛ (лента та же).
;;; ============================================================

;; Принтер из настроек ПСПНАСТРОЙКИ (пустое значение = FinePrint)
(defun psp-fp-printer (key / s)
  (setq s (getcfg key))
  (if (and (= (type s) 'STR) (/= s "")) s "FinePrint"))

;; Эффективный формат рамки: номинал формата СПДС; кратность
;; X2/X3 поднимает формат по шагам (A4X2 -> A3, A4X3 -> A2).
(defun psp-fp-frame-format (fmt / p base mult)
  (setq p (psp-spds-parse (psp-spds-norm fmt)))
  (if p
    (progn
      (setq base (nth 0 p) mult (nth 1 p))
      (while (> mult 1)
        (setq base (nth 0 (psp-spds-size-up base)) mult (1- mult)))
      base)
    nil))

;; Предустановка бумаги СИСТЕМНОГО принтера активному листу
;; (механика FP: ConfigName = принтер, CanonicalMediaName = A4/A3
;; с readback; если драйвер отверг имя — ищем его бумагу по маске
;; в списке бумаг драйвера). Прежние устройство/бумага сохраняются
;; в *psp-page-saved* — восстановление штатным psp-page-restore.
;; Возвращает фактическое имя бумаги или nil.
(defun psp-fp-preset (printer fmt / doc layout cfg med names found)
  (setq *psp-page-saved* nil)
  (setq doc (psp-get (vlax-get-acad-object) 'ActiveDocument))
  (setq layout (psp-get doc 'ActiveLayout))
  (if (or (null layout) (vl-catch-all-error-p layout))
    nil
    (progn
      (setq cfg (psp-get layout 'ConfigName)
            med (psp-get layout 'CanonicalMediaName))
      (setq *psp-page-saved*
            (list (if (vl-catch-all-error-p cfg) nil cfg)
                  (if (vl-catch-all-error-p med) nil med)))
      (psp-safe-put layout 'ConfigName printer)
      (psp-safe-put layout 'CanonicalMediaName fmt)
      (setq med (psp-get layout 'CanonicalMediaName))
      (if (or (vl-catch-all-error-p med)
              (not (wcmatch (strcase (if (= (type med) 'STR) med ""))
                            (strcat (strcase fmt) "*"))))
        (progn
          (setq names (vl-catch-all-apply
                        '(lambda ( )
                           (vlax-invoke layout 'GetCanonicalMediaNames))))
          (if (and (not (vl-catch-all-error-p names))
                   (= (type names) 'LIST))
            (progn
              (setq found nil)
              (foreach nm names
                (if (and (null found)
                         (= (type nm) 'STR)
                         (wcmatch (strcase nm)
                                  (strcat "*" (strcase fmt) "*")))
                  (setq found nm)))
              (if found
                (psp-safe-put layout 'CanonicalMediaName found))))))
      (setq med (psp-get layout 'CanonicalMediaName))
      (if (vl-catch-all-error-p med) nil med))))

;; Лента печати на системный принтер — дословно лента FP 1.03
;; (формат не посылается: бумага предустановлена psp-page-preset)
(defun psp-fp-plot-tape (printer rot ctb x1 y1 x2 y2 / old-cmdecho)
  (setq old-cmdecho (getvar "CMDECHO"))
  (setvar "CMDECHO" (if *fp-plot-echo* 1 0))
  (command "_.-plot"
            "_Y"
            ""
            printer
            ""
            "_M"
            rot
            "_N"
            "_W"
            (list x1 y1)
            (list x2 y2)
            "_F"
            "_C"
            "_Y"
            ctb
            "_Y")
  (if (= 1 (getvar "TILEMODE"))
    (command "_As" "_N" "" "_Y")
    (command "_N" "_N" "_N" "_N" "" "_Y"))
  (setvar "CMDECHO" old-cmdecho))

(defun c:ЭКССПДСФП ( / ss n i ent obj it items fmt sheet sheet-i bb
                        w h fname fmtbase paper printer rot ctb x1 y1 x2 y2
                        nm-n used ok-list skip j row p4a p3a res stuck
                        old-bg old-paper)
  (princ "\nЭкспорт форматов СПДС на принтер. Выберите объекты (или All).")
  (setq ss (ssget (list (cons 0 *psp-spds-entity*))))
  (cond
    ((null ss) (princ "\nОтменено.") (princ))
    (t
     (setq n (sslength ss) i 0 items nil skip nil)
     (princ (strcat "\nПСП: выбрано объектов: " (itoa n)))
     (while (< i n)
       (setq ent (ssname ss i))
       (setq obj (vlax-ename->vla-object ent))
       (setq flds (psp-spds-fields ent))
       (setq fmt (psp-field flds "Format"))
       (if (null fmt)
         (setq fmt (psp-spds-prop obj *psp-spds-props-format*)))
       (setq sheet (psp-field flds "Sheet"))
       (if (null sheet)
         (setq sheet (psp-spds-prop obj *psp-spds-props-sheet*)))
       (setq sheet-i (psp-sheet-num sheet))
       (setq bb (psp-spds-bbox obj))
       (if bb
         (setq items
               (cons (list ent obj fmt
                           (if (psp-sheet-p sheet) sheet-i 9999.0)
                           (car bb) (cadr bb) (caddr bb) (cadddr bb)
                           sheet)
                     items))
         (setq skip (cons (cdr (assoc 5 (entget ent))) skip)))
       (setq i (1+ i)))
     (setq items (psp-spds-sorted (reverse items)))
     (princ (strcat "\nПСП: к печати после сортировки: " (itoa (length items))))
     (cond
       ((null items)
        (princ "\nУ выбранных объектов нет габаритов — печатать нечего.")
        (princ))
       (t
        (setq p4a (psp-fp-printer "AppData/PlotFrame/FPPrinterA4")
              p3a (psp-fp-printer "AppData/PlotFrame/FPPrinterA3")
              ctb (if *psp-color-mode* *psp-ctb-color* *psp-ctb-mono*))
        (princ (strcat "\nПСП: принтер A4: " p4a " | принтер A3+: " p3a
                       " | печать: " (if *psp-color-mode* "цвет" "ч/б")
                       " (" ctb ") | масштаб: Вписать"))
        (setq old-bg (getvar "BACKGROUNDPLOT")
              old-paper (vl-catch-all-apply
                          '(lambda ( ) (getvar "PAPERUPDATE"))))
        (setvar "BACKGROUNDPLOT" 0)
        (if (not (vl-catch-all-error-p old-paper))
          (setvar "PAPERUPDATE" 0))
        (setq used nil ok-list nil j 0)
        (foreach it items
          (setq w (- (nth 6 it) (nth 4 it))
                h (- (nth 7 it) (nth 5 it))
                fmtbase (if (nth 2 it)
                          (psp-fp-frame-format (nth 2 it))
                          nil)
                paper (if (= fmtbase "A4") "A4" "A3")
                printer (if (= fmtbase "A4") p4a p3a)
                rot (if (>= w h) "_L" "_P")
                nm-n (psp-spds-uniq
                       (if (nth 8 it)
                         (psp-sheet-name (nth 8 it))
                         (strcat "L" (psp-pad2 (1+ j))))
                       used)
                used (cadr nm-n))
          (princ (strcat "\n  ПСП: " (car nm-n)
                         " (" (if (nth 2 it) (nth 2 it) "?")
                         " -> " paper " на " printer ")"))
          (setq res (vl-catch-all-apply 'psp-fp-preset (list printer paper)))
          (if (vl-catch-all-error-p res)
            (princ (strcat "\n  ПСП: предустановка ОШИБКА: "
                           (vl-catch-all-error-message res)))
            (princ (strcat "\n  ПСП: предустановка: "
                           (if (= (type res) 'STR) res "НЕ ПРИМЕНИЛАСЬ"))))
          (setq x1 (car (trans (list (nth 4 it) (nth 5 it)) 0 1))
                y1 (cadr (trans (list (nth 4 it) (nth 5 it)) 0 1))
                x2 (car (trans (list (nth 6 it) (nth 7 it)) 0 1))
                y2 (cadr (trans (list (nth 6 it) (nth 7 it)) 0 1)))
          (setq stuck nil)
          (psp-fp-plot-tape printer rot ctb x1 y1 x2 y2)
          (psp-page-restore)
          (if (> (getvar "CMDACTIVE") 0)
            (progn
              (princ "\n  ПСП: -ПЕЧАТЬ застряла — вторая попытка.")
              (psp-clear-stuck)
              (psp-fp-preset printer paper)
              (psp-fp-plot-tape printer rot ctb x1 y1 x2 y2)
              (psp-page-restore)
              (if (> (getvar "CMDACTIVE") 0)
                (progn
                  (princ "\n  ПСП: повторно застряла — лист пропущен.")
                  (psp-clear-stuck)
                  (setq stuck T)))))
          (if stuck
            (setq skip (cons (car nm-n) skip))
            (setq ok-list
                  (cons (list (car nm-n)
                              (if (nth 2 it) (nth 2 it) "?")
                              paper printer)
                        ok-list)))
          (setq j (1+ j)))
        (setvar "BACKGROUNDPLOT" old-bg)
        (if (not (vl-catch-all-error-p old-paper))
          (setvar "PAPERUPDATE" old-paper))
        (setq ok-list (reverse ok-list))
        (princ "\nПечать СПДС на принтер:")
        (princ "\n  | лист   | формат СПДС | бумага | принтер            |")
        (princ "\n  |--------|-------------|--------|--------------------|")
        (foreach row ok-list
          (princ (strcat "\n  | "
                         (psp-pad-right (nth 0 row) 6) " | "
                         (psp-pad-right (nth 1 row) 11) " | "
                         (psp-pad-right (nth 2 row) 6) " | "
                         (nth 3 row) " |")))
        (princ (strcat "\nГотово: " (itoa (length ok-list))
                       " из " (itoa (length items))
                       (if skip
                         (strcat "; пропущено: "
                                 (itoa (length skip)))
                         "")))
        (princ))))
     )
  (princ))

;; Английский псевдоним ЭКССПДСФП
(defun c:EXPSPDSFP () (c:ЭКССПДСФП))

;; без эха результата загрузки
(princ)
