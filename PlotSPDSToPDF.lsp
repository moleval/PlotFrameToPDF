;;; -*- coding: windows-1251 -*-
;;; PlotSPDSToPDF.lsp
;;;
;;; Серийная печать выбранных форматов СПДС GraphiCS (SPDSFORMAT)
;;; с сортировкой по листам. Диагностика ЭКССПДСДИАГ — в файле
;;; PlotSPDSDiag.lsp (модуль 2 — загрузить ПОСЛЕ этого файла).
;;;
;;; Команды: ЭКССПДСВПДФ / SPDSTOPDF — серийный экспорт в PDF
;;;          ПСППАПКА / PSPPAPKA — открыть папку журналов
;;;          ЭКССПДСВПДФ / SPDSTOPDF — серийный экспорт в PDF
;;;
;;; Кодировка: CP1251 (ANSI), без BOM.
;;; v0.2: GetBoundingBox через vl-catch-all-apply привязывает к символам
;;;        СЫРОЙ safearray (не variant) — незащищённый vlax-variant-value
;;;        падал с «неверный тип аргумента: variantp». Добавлен
;;;        конвертер psp-va->list (variant -> значение, safearray
;;;        проходит насквозь); разбор строки таблицы диагностики
;;;        обёрнут в перехват — один плохой объект не роняет отчёт.
;;; v0.3: по дампу подтверждено: ObjectName = mcsDbObjectFormat,
;;;        кастомных COM-свойств у объекта НЕТ — формат/лист/листов
;;;        лежат в данных примитива. Добавлен универсальный экстрактор:
;;;        текстовые группы entget (1, 3), бинарные группы (310-312)
;;;        с раскодировкой hex и извлечением читаемых строк, XRecord'ы
;;;        расширения словаря, XData. Автопоиск кандидатов формата.
;;; v0.4: по логу v0.3: у объекта нет ни словаря (HasExtensionDictionary
;;;        = 0), ни текстов в entget — данные формата СПДС держит в своей
;;;        базе. Основной канал — план Б: ТЕКСТЫ штампа в области рамки
;;;        (TEXT/MTEXT/ATTRIB по габаритам объекта, сортировка сверху
;;;        вниз). Добавлен скан текстов; XData (группы 1000+) добавлен
;;;        в экстрактор; исправлен разбор вариантов XRecord.
;;; v0.5: по логу v0.4: HasExtensionDictionary = -1 — словарь ЕСТЬ,
;;;        но XRecord'ов в нём не нашлось (COM-обход не увидел).
;;;        Добавлен глубокий обход словаря расширения через dictnext
;;;        (группа 360 entget; вложенные словари рекурсивно; XRecord'ы
;;;        читаются entget'ом напрямую). Диагностика области расширена:
;;;        все типы объектов в окне, блоки, атрибуты, тексты из
;;;        определений блоков. ПроверкаPlotSPDS: закрытый продукт,
;;;        функциональный ориентир — сортировка/имёнование/многопаг PDF.
;;; v0.6: v0.5 не загрузилась у пользователя («синтаксическая ошибка»),
;;;        хотя строгий сторонний Lisp-ридер читает файл без ошибок.
;;;        Добавлены маркеры прогресса загрузки по секциям — последний
;;;        напечатанный маркер указывает секцию со сбоем.
;;;        Новая команда ПСППАПКА — открывает папку журналов в Проводнике.
;;; v0.7: найдена и исправлена причина сбоя v0.5/v0.6: маркер секции 7
;;;        был вставлен В СЕРЕДИНУ строки комментария, его хвост
;;;        «строки (1,3,1000),» становился кодом — AutoCAD пытался
;;;        вызвать (1,3,1000) как функцию. Комментарий восстановлен.
;;; v0.8: сбой сместился в секцию 8 (большой defun диагностики).
;;;        Диагностика разбита на НЕСКОЛЬКО верхнеуровневых функций
;;;        с маркерами 8a/8b/8c между ними — следующий сбой укажет
;;;        подблок точно. (apply '+ ...) заменён на явную сумму.
;;; Маркер редакции для RELOAD: (ред. 85
;;; v0.85: рамки качества — снова В СТРОКУ, но с фиксированными
;;;        слотами 23/16/16: «Низкое/Среднее/Высокое» обеих рамок
;;;        стоят на одних вертикалях. Поле пути обёрнуто в :row,
;;;        как автосборка/задержка, — правый край пути = правому
;;;        краю полей (60 = 30+30).
;;; v0.84: таблица настроек: линии рамки совпадают по ширине со
;;;        строками (колонка = «|»+пробел+28/34) — правые «+» боль-
;;;        ше не вываливаются за вертикали строк.
;;; v0.83: поле пути — на всю внутреннюю ширину рамки (60, метка
;;;        «Папка:» убрана — есть заголовок рамки). Радиокнопки ка-
;;;        чества — вертикальной колонкой в обеих рамках, подписи
;;;        рамки в PDF без «авто»: «Низкое (-1) / Среднее / Высо-
;;;        кое (+1)» — колонки обеих рамок выровнены по вертикали.
;;; v0.82: окно — всё в рамках с единой сеткой (подписи 30 вправо,
;;;        поля 30): блок 1 «Папка сохранения» (строка 2 = подсказка
;;;        + «Обзор...»), блок 2 «Сборка и результат» (автосборка,
;;;        задержка, обе галочки). Таблица настроек — ПОЛНАЯ рамка:
;;;        вертикали до и после колонок, линии сверху/после шапки/
;;;        снизу, значения добиваются пробелами до ширины колонки.
;;; v0.81: таблица настроек — С ЯЧЕЙКАМИ (вертикальный разделитель
;;;        «|», «+» на стыке). В окне строки «CTB для ч/б/цвета»
;;;        переименованы в «Чёрно-белая печать» / «Цветная печать»;
;;;        сетка: правый край всех полей по одной линии — списки 30,
;;;        поля автосборки/задержки 30, папка(21)+Обзор(9) = 30.
;;; v0.80: окно «Настройки печати» переработано: сетка — подписи
;;;        30 знаков вправо, все списки шириной 30; принтеры PDF/A4/
;;;        A3 одной колонкой; «Цветная печать (выкл=ч/б)» заменена
;;;        парой радио «Чёрно-белая печать»/«Цветная печать»; рамки
;;;        качества переименованы («Качество печати "Рамка в PDF"…»);
;;;        «Низкое (формат в формат)» -> «Низкое (по формату)».
;;; v0.79: чат «секция N/10 загружена» УБРАН: успешная загрузка —
;;;        один баннер «Загружено: …», ошибка — AutoCAD печатает сам
;;;        у проблемной формы. Отчёт настроек после «Применить» —
;;;        ПОЛНОЙ таблицей (параметр/значение, выравнивание
;;;        psp-pad-right, подчёркивание дефисами).
;;; v0.78: после «настройки сохранены» в консоль печатается список
;;;        применённых параметров: папка, PDF-принтер, цвет+CTB,
;;;        принтеры FP (A4/A3), автосборка, задержка, открытие,
;;;        удаление, качество СПДС и рамки.
;;; v0.77: умолчание списков FP-принтеров: пустое значение реестра
;;;        (= отсутствующий ключ) больше не выбирает первый принтер
;;;        списка — всегда FinePrint.
;;; v0.76: ПСПНАСТРОЙКИ: рамочка печати на принтер (FP-модуль
;;;        ЭКСВПФПА4/ЭКСВПФПА3) — два выпадающих списка СИСТЕМНЫХ
;;;        принтеров Windows (реестр HKLM Control\Print\Printers,
;;;        полный перечень; FinePrint добавлен, если отсутствует),
;;;        отдельный для A4 и для A3; хранение AppData/PlotFrame/
;;;        FPPrinterA4/A3, умолчание FinePrint.
;;; v0.75: папка сборки — просто <имя чертежа> (без даты), альбом
;;;        внутри — по-прежнему <имя>_<дата>_<время>.pdf: повторные
;;;        сборки накапливаются в одной папке, альбомы не затирают
;;;        друг друга.
;;; v0.74: (1) папка сборки названа по чертежу, как и альбом:
;;;        <имя>_<дата>_<время> (была SPDS_<штамп>); (2) найдена
;;;        причина «склеилось 5/6 из 7»: GS создаёт файл сразу, а
;;;        дописывает ПОСЛЕДНИМ — ожидание шло по первому появлению
;;;        файла, зритель открывал НЕДОПИСАННЫЙ альбом; теперь ждём
;;;        стабилизации размера (3 одинаковых замера по 0.5 с);
;;;        (3) в логе размер каждого входа (0 байт = выпавшая
;;;        страница); (4) проверка альбома перед открытием — в LISP,
;;;        нет файла -> открывается папка сборки.
;;; v0.73: три правки открытия/склейки: (1) расширение чертежа
;;;        отрезается по верной позиции (0.72 смотрел k-1 вместо
;;;        k-3 — в имени оставалось «.dwg»); (2) перед склейкой
;;;        печатается список ОТСУТСТВУЮЩИХ входов, после — размер
;;;        альбома (диагностика «склеилось меньше листов»);
;;;        (3) если альбома нет в момент открытия — открывается
;;;        папка сборки (вместо тишины).
;;; v0.72: имя чертежа берётся из DWGNAME (с отрезанием расшире-
;;;        ния), а не DWGTITLED — тот есть флаг 0/1, из-за него
;;;        0.71 всегда давал запасное «SPDS».
;;; v0.71: склеенный альбом называется <имя чертежа>_<дата>_<время>
;;;        .pdf (DWGTITLED + штамп CDATE; несохранённый чертёж —
;;;        «SPDS»). Папка сборки осталась SPDS_<дата>_<время> — под
;;;        маску удаления L*.pdf альбом не попадает, как и раньше.
;;; v0.70: ЦВЕТ ЕДИНЫЙ ДЛЯ ОБОИХ: рамочка задачи 12 раньше писала
;;;        только *pfp-* (база), а СПДС печатает по *psp-color-mode*/
;;;        *psp-ctb-* — оставался ч/б. Теперь Apply применяет к обоим
;;;        пространствам, load-cfg подхватывает в оба, диалог читает
;;;        из *psp-* (всегда объявлены). Один источник — реестр
;;;        AppData/PlotFrame/{ColorMode,CtbMono,CtbColor}.
;;; v0.69: реестр отравлен частичным Apply 0.67 (PC3="T" — в баннере
;;;        «Принтер: T»): PC3 теперь принимается/сохраняется ТОЛЬКО
;;;        при маске *.pc3; все *psp-t-* читаются через строгую
;;;        psp-str-or (не-строка -> умолчание), setcfg значений —
;;;        через psp-s->str; сообщение об ошибке диалога печатает
;;;        ЭТАП (заполнение списков / диалог / сохранение настроек).
;;; v0.68: ПСПНАСТРОЙКИ не должна ломать печать: старт диалога и
;;;        блок «Применить» обёрнуты в vl-catch-all-apply, unload_di-
;;;        alog гарантирован при ЛЮБОМ исходе (живой диалог блокирует
;;;        -ПЕЧАТЬ — инцидент 0.67: «stringp T» + 0 из 4 листов); сам
;;;        текст ошибки печатается в консоль. psp-popup-fill игнори-
;;;        рует не-строки; перечисление .pc3/.ctb переведено на флаг
;;;        «только файлы» (1) — прежний -1 читал только ПОДПАПКИ.
;;; v0.67: задача 12 — в ПСПНАСТРОЙКИ добавлена рамочка «Цвет и
;;;        стили печати (ЭКСВПДФ)» под выбором принтера: переключатель
;;;        Цветная печать (выкл = ч/б) и два выпадающих списка CTB
;;;        (для ч/б и для цвета; все .ctb из папки стилей AutoCAD,
;;;        PrinterStyleSheetDir; недоступна — monochrome/acad + теку-
;;;        щие значения). Сохранение: AppData/PlotFrame/{ColorMode,
;;;        CtbMono,CtbColor} + живое применение в загруженную базу.
;;; v0.66: задача 3 — портативный Ghostscript: в psp-find-gs добавле-
;;;        на страховая ветка GS[3.5] (<диск>:\PlotFrameToPDF\gs\bin
;;;        \gswin64c.exe, диски C:/D:/E:, папка проверяется vl-file-
;;;        directory-p). Срабатывает, когда нет ни ПСПГС, ни реестра,
;;;        ни Program Files. Распакованный gs кладётся пользователем
;;;        в D:\PlotFrameToPDF\gs (в git не попадает, .gitignore).
;;; v0.65: хвост ленты Листа: ПОСТОЯННЫХ ответов стало три («масш-
;;;        штабировать веса», «печатать лист первым», «скрывать
;;;        объекты листа»); вопрос «записать изменения в макет»
;;;        задаётся ТОЛЬКО при расхождении с сохранёнными парамет-
;;;        рами листа — под него больше нет постоянного ответа,
;;;        вместо этого: сбой ленты перехватывается и выполняется
;;;        ВТОРАЯ ПОПЫТКА с четвёртым «Нет» (alt). Феномен «_N.pdf»
;;;        в папке чертежа устранён (ответ уезжал в имя файла).
;;; v0.64: устранён nil в ленте command (защита 0.63 возвращала nil —
;;;        в ряде сборок это убивает -ПЕЧАТЬ на вопросе о формате).
;;;        Теперь: Лист — всегда «Enter» (формат уже предустановлен,
;;;        лист хранит портретный канон), Модель — фактически приняв-
;;;        шийся формат (readback), при полном провале — плановое имя.
;;; v0.63: имя формата шлётся в -ПЕЧАТЬ ТОЛЬКО когда предустановка
;;;        (psp-page-preset, ActiveX) его реально приняла — теперь
;;;        psp-page-preset ВОЗВРАЩАЕТ фактический CanonicalMediaName.
;;;        Отвергнутое листом имя (альбомный канонический на Листе,
;;;        отсутствующий размер) роняет -ПЕЧАТЬ; вместо него шлётся
;;;        «Enter» — берётся фактический формат листа.
;;; v0.62: ПЕЧАТЬ С ВКЛАДКИ ЛИСТ починена: в ленте Листа 4 ответа
;;;        «Нет» перед именем файла (масштабировать веса / лист
;;;        последним / скрывать объекты листа / НЕ записывать изменения
;;;        в макет), а формат бумаги на Листе не посылается вовсе —
;;;        он уже предустановлен (psp-page-preset), альбомное имя не
;;;        совпадает с каноническим и срывало ленту после вопроса о
;;;        формате. «Масштабировать веса» (ПСПЛЕНТА) остался только
;;;        в ветке Модели.
;;; v0.61: ПСПНАСТРОЙКИ: принтер — ВЫПАДАЮЩИЙ СПИСОК всех .pc3 из
;;;        папки конфигураций плоттеров (PrinterConfigDir; если папка
;;;        недоступна — текущий + DWG To PDF.pc3). Папка сохранения —
;;;        кнопка «Обзор...»: диалог выбора папки Windows (Shell;
;;;        без COM — сообщение и ввод вручную).
;;; v0.60: ПАПКА СОХРАНЕНИЯ теперь общая и рабочая: настроенная папка
;;;        становится *psp-output-dir* — СПДС печатает листы и кладёт
;;;        склейку в <папка>\SPDS_<штамп>; перенос (move) больше не
;;;        нужен, блок удалён. База (если загружена) получает ту же
;;;        папку (AppData/PlotFrame/OutDir). Диалог: две РАМОЧКИ
;;;        качества — «Рамочка в PDF» и «Формат СПДС в PDF»; подписи
;;;        Низкое/Среднее/Высокое (пробелы в «авто -1», «авто +1»);
;;;        ПСПКАЧ: Высокое вместо Отличного.
;;; v0.59: подписи радиостроки базы в ПСПНАСТРОЙКИ: Низкое (авто-1) /
;;;        Среднее (авто) / Отличное (авто+1) — схема изменена в базе
;;;        3.20: сдвиг формата от авто-выбора, множитель не трогается.
;;; v0.58: лестница качества полностью переписана (заменяет
;;;        дефектный коммит 7f5d110, в который исправление не попало):
;;;        0 = формат-в-формат через psp-format-idx (parse даёт ИМЯ,
;;;        запись даёт только format-idx/size-up — иначе consp "A4");
;;;        1 = один psp-spds-size-up; 2 = size-up -> имя записи ->
;;;        size-up (второй прыжок по имени: раньше на вход шла ЗАПИСЬ,
;;;        format-idx давал nil, срабатывал fallback (nth 3) = A1 —
;;;        отсюда A1 при «Отличном» в логе 0.56).
;;; v0.56: качество базового PlotFrameToPDF (ЭКСВПДФ) — вторая
;;;        радиострока в ПСПНАСТРОЙКИ (rq0/rq1/rq2 = x1/x2/x4,
;;;        setcfg AppData/PlotFrame/Quality; при загруженной базе
;;;        применяется сразу). В базе 3.19: *pfp-quality* читается
;;;        на прогоне и задаёт *pfp-size-factor* (1/2/4).
;;; v0.55: ЗАДАЧА «КАЧЕСТВО ПЕЧАТИ»: *psp-quality* 0/1/2 —
;;;        Низкое=формат в формат, Среднее=+1 (как всегда), Отличное=+2.
;;;        Выбор: команда ПСПКАЧ / PSPQUAL и радиострока в диалоге
;;;        настроек; хранение setcfg AppData/PlotSPDS/Quality.
;;; v0.54: поля всё ещё приходили пустыми: в ряде версий AutoCAD
;;;        get_tile НЕ работает после закрытия диалога. Значения
;;;        читаются в callback кнопки «Применить» (psp-tiles-read)
;;;        ДО done_dialog; блок сохранения использует *psp-t-*.
;;; v0.53: «неверный тип аргумента: stringp nil», папка не сохранялась:
;;;        unload_dialog стоял ДО чтения get_tile (после выгрузки
;;;        get_tile возвращает nil). Порядок исправлен: значения
;;;        читаются до выгрузки; все get_tile обёрнуты в psp-s->str.
;;; v0.52: DCL-диалога: у тайла spacer нельзя переопределять width
;;;        (фиксированный размер) — «неверный атрибут. Символ: spacer»,
;;;        строка 9. Заменено на безатрибутный spacer.
;;; v0.51: ИСПРАВЛЕНА «синтаксическая ошибка» при загрузке: в хвосте
;;;        диалога настроек 0.50 закрывающая скобка встала так, что
;;;        (princ) попал в форму (if ...) четвёртым аргументом; баланс
;;;        скобок при этом не нарушался (поэтому статическая батарея
;;;        молчала), а загрузчик AutoCAD форму отвергал. В батарею
;;;        добавлен тест арности if (2-3 аргумента).
;;; v0.50: ОКНО НАСТРОЕК ПСПНАСТРОЙКИ / PSPSET (DCL генерируется во
;;;        временную папку; хранение — реестр setcfg, восстановление
;;;        при загрузке psp-load-cfg): папка сохранения PDF (gs
;;;        собирает в temp, альбом переносится cmd move, открытие —
;;;        уже из новой папки), порог автосборки N (раньше 3), таймер
;;;        открытия (раньше 5), имя PDF-принтера (раньше только
;;;        глобальная), «Открывать результат», «Удалять одиночные».
;;;        Гейт *psp-open-pdf* заменён на *psp-open-res*.
;;; v0.49: по пользователю: при отказе от склейки (2-3 листа)
;;;        одиночные листы ОТКРЫВАЮТСЯ (через ~5 с, фоновый cmd), то же
;;;        для единственного листа. С «тихим» принтером это безопасно:
;;;        вкладки больше не плодит принтер (0.47/0.48).
;;; v0.48: по пользователю: принтер по умолчанию — PlotSPDSToPDF.pc3
;;;        (его «тихая» копия DWG To PDF.pc3 без галочки «Показывать
;;;        результаты в программе просмотра»). Добавлена справка
;;;        ПСППОМОЩЬ / PSPHELP / PSPPOMOSH: команды, порядок листов,
;;;        автосборка, пошаговое создание копии принтера (папка —
;;;        getenv PrinterConfigDir, ПЛОТТЕРМАНАДЖЕР не обязателен).
;;;        Баннер загрузки печатает имя принтера.
;;; v0.47: разгадка «самооткрывающихся» листов: DWG To PDF.pc3 ->>
;;;        «Параметры PDF» -> «Показывать результаты в программе
;;;        просмотра» — принтер сам открывает каждый отпечатанный
;;;        лист. На лету галочку не переключить (бинарный pc3),
;;;        введена глобальная *psp-pc3* (по умолчанию "DWG To
;;;        PDF.pc3"): пользователь один раз делает «тихую» копию
;;;        принтера без галочки и задаёт её имя. Сохранение в команде
;;;        настроек (задача 4/7).
;;; v0.46: по просьбе пользователя одиночные листы НЕ открываются
;;;        ВООБЩЕ (0.45 открывал их при отказе от склейки и при одном
;;;        листе — пользователь подтвердил: открывать только склейку).
;;;        Нет склейки — просто открывается папка сборки.
;;; v0.45: схема пользователя: склеиваем «закрытыми», открываем
;;;        ТОЛЬКО склейку; одиночные листы сами не запускаем. Если
;;;        склейки нет — открываем одиночные: при ответе «Нет» (2-3
;;;        листа) и при единственном листе (задержка ~5 с в фоновом
;;;        cmd). Вторая волна удаления остаётся страховкой от вкладок
;;;        просмотрщика.
;;; v0.44: диагностика: с закрытым просмотрщиком del с маской чист,
;;;        с открытым — ошибки «файл занят» (PDF-XChange блокирует
;;;        открытые вкладки). Добавлена вторая волна: фоновый цикл
;;;        del каждые ~5 с в течение ~1 мин — листы удаляются, как
;;;        только просмотрщик закрывают.
;;; v0.43: журнал 0.42: альбом открылся, но одиночные листы остались —
;;;        цепочка из 18 отдельных del не доводилась (длинная команда).
;;;        Диагностика подтвердила: короткая команда с маской работает.
;;;        Удаление одной командой: del "dir\L*.pdf" (альбом SPDS_*
;;;        маску не попадает).
;;; v0.42: задача «автоудаление одиночных файлов»: при УСПЕШНОЙ
;;;        склейке одиночные листы (pdfs) удаляются тем же фоновым
;;;        cmd с той же задержкой ~5 с: ping -> del листов -> start
;;;        склейки. Если склейка не состоялась (отказ «Нет», ошибка,
;;;        нет GS) — листы не трогаются. psp-open-pdf принял второй
;;;        аргумент dels.
;;; v0.41: журнал 0.40 показал: просмотрщик ЗАПУСКАЛСЯ, но ловил
;;;        «процесс не может получить доступ к файлу» — gs создаёт
;;;        выходной PDF сразу, а закрывает последним; открытие по факту
;;;        появления файла было гонкой. Открытие отложено на ~5 с
;;;        (ping -n 6) внутри фонового cmd: gs к тому моменту завершён.
;;; v0.40: диагностика на машине пользователя: вручную из консоли
;;;        открывались ВСЕ механизмы (cmd start, explorer, rundll32),
;;;        но старт из работающего LISP — нет (DDE-ассоциация .pdf,
;;;        PDF-XChange; без прокачки сообщений запуск терялся).
;;;        Новый psp-open-pdf: основной запуск через explorer.exe
;;;        (своя очередь сообщений), запасные rundll32 и cmd start;
;;;        каждое звено пишет T/nil в консоль.
;;; v0.39: по согласованию: после успешной сборки PDF открывается
;;;        системным просмотрщиком (startapp cmd /c start, путь в
;;;        кавычках с пустым заголовком). Выключатель *psp-open-pdf*
;;;        (по умолчанию T); команда настроек появится позже.
;;; v0.38: лист «0» — титульный: идёт перед листом 1 (раньше «0»
;;;        приравнивался к «без номера» и попадал в конец). Номер —
;;;        настоящий, если строка непуста и состоит из цифр, точек
;;;        и запятых (psp-sheet-p); имя файла — L00. Безномерные
;;;        листы по-прежнему в конце.
;;; v0.37: по просьбе пользователя откатлено расширение окна печати
;;;        (*psp-margin* удалён): окно = bbox прокси-объекта, как раньше.
;;;        Автосборка в один PDF при >3 листах осталась.
;;; v0.36: по запросу пользователя: больше трёх листов — сборка в один
;;;        PDF выполняется автоматически (вопрос остался для 2-3).
;;;        Лист 15.1 обрезался: bbox прокси-объекта СПДС (297.00x409.16)
;;;        меньше видимого кадра; окно печати расширено на *psp-margin*
;;;        (2% большей стороны, настраивается) — «Вписать» компенсирует.
;;; v0.35: по запросу пользователя: дробные листы (15, 15.1, 15.2)
;;;        идут по порядку номеров. Ранее atoi("15.1")=15 — все имели
;;;        один ключ и сортировались по вертикали. Номер парсится как
;;;        вещественный (psp-sheet-num), имена файлов честные:
;;;        L15, L15.1, L15.2 (psp-sheet-name), в таблице без ".0"
;;;        (psp-num-str). Строка номера хранится в позиции 8 записи.
;;; v0.34: 18/18 ЛИСТОВ В РЕАЛЬНОМ АЛЬБОМЕ (A4->A3 и A3->A2, обе
;;;        ориентации, дубликаты L15_2/_3) — печать стабильна. Склейка
;;;        во ВТОРОМ чертеже упала «no function definition:
;;;        PSP-S->STR»: переписка find-gs в 0.32 (срез «от find-gs до
;;;        merge-pdfs») молча удалила определение psp-s->str; в первом
;;;        чертеже её спасала старая загрузка v0.26 в той же сессии.
;;;        Функция возвращена.
;;; v0.33: СКЛЕЙКА ЗАРАБОТАЛА (ПСПГС -> GS[1] -> «Собрано в один PDF»),
;;;        но файл был пуст (одна белая страница): в список склейки
;;;        собирались ГОЛЫЕ имена (L01.pdf), gs искал их в своём рабочем
;;;        каталоге и не находил. Теперь в склейку идут полные пути.
;;;        Строка GS[4] печатается только если сработала ветка 4.
;;; v0.32: лог 0.31 показал: сработала ветка «рядом с чертежом» и
;;;        отдала ВЫДУМАННЫЙ путь (после 0.31 пути доверяются без
;;;        проверки) — GS_DLL из реестра даже не читался. Приоритет
;;;        изменён: реестр ПЕРВЫМ (там фактический каталог установки),
;;;        выдуманные пути рядом с чертежом — последними; логи только
;;;        от реально отработавших веток.
;;; v0.31: лог 0.30 добил: «GS_DLL -> type=STR», затем stringp T —
;;;        open тоже подменён (возвращает T для существующего файла),
;;;        а (close T) вне catch-all поднимал ошибку. Проверки файлов
;;;        в поиске GS убраны ВООБЩЕ: путь доверяется, существование
;;;        подтвердит сама склейка (выходной PDF появился — путь верный;
;;;        нет — таймаут и подсказка ПСПГС).
;;; v0.30: в 0.29 поиск GS не запускался вовсе — vl-catch-all-apply
;;;        получил (list nil) как аргумент для функции без аргументов
;;;        («слишком много аргументов»); вызов исправлен на nil.
;;; v0.29: лог 0.28 добил: «GS_DLL -> type=STR» напечатан, а следующий
;;;        strcat упал — vl-filename-directory ТОЖЕ возвращает T (хуки
;;;        СПДС затрагивают и его). Модуль отвязан от vl-filename-*:
;;;        каталог/имя разбираются вручную (psp-file-dir/psp-file-base
;;;        на substr), существование файла — open/close (findfile
;;;        остался только индикатором). Поиск GS обёрнут в catch-all
;;;        с печатью ошибки; команда ПСПГС — ручной путь.
;;; v0.28: НАЙДЕНА ОКОНЧАТЕЛЬНАЯ ПРИЧИНА ВСЕХ «stringp T»: findfile
;;;        у пользователя возвращает T вместо пути существующего файла
;;;        (подозрение на вмешательство СПДС GraphiCS). Улики: «TT» в
;;;        тесте 0.19, gs=T в 0.26, падение сразу после «type=STR» на
;;;        strcat с результатом поиска. try теперь возвращает
;;;        собственный путь, а не результат findfile. Добавлена команда
;;;        ПСПГС / PSPGS: задать путь к Ghostscript вручную и запомнить
;;;        (setcfg, восстанавливается при загрузке).
;;; v0.27: склейка показала gs=T — psp-find-gs вернул T вместо пути
;;;        (старый тест пользователя (princ (psp-find-gs)) -> «TT»,
;;;        тот же случай). Поиск инструментирован: каждый этап печатает
;;;        результат; в реестре читаются GS_DLL и GS_LIB (10.x);
;;;        наружу проходит только строка, не-строка -> nil.
;;; v0.26: печать 4/4 прошла, но склейка упала «stringp T» — источник
;;;        статически не найден. Склейка сделана пуленепробиваемой:
;;;        все части команды через psp-s->str (не-строка НЕ роняет
;;;        strcat, а видна в печатаемой команде), вызов под
;;;        vl-catch-all с печатью ошибки, gs и целевой путь печатаются
;;;        до склейки — следующий лог покажет всё.
;;; v0.25: ТРАНСКРИПТ 0.24 РАСКРЫЛ ПРИЧИНУ: подсказке «Введите имя
;;;        файла» уходил ответ «_As» — в общей ленте был ЛИШНИЙ ответ
;;;        «_N» («не масштабировать веса»): в этой сборке AutoCAD такого
;;;        вопроса нет, и лента сбита на один токен с этого места.
;;;        Лишний ответ убран; на случай других сборок — переключатель
;;;        ПСПЛЕНТА / PSPTAPE (добавить «_N» обратно). Предустановка
;;;        листа подтверждена транскриптом (формат применен).
;;; v0.24: гипотеза о вкладке Листа не подтвердилась (пользователь
;;;        запускал из модели) — принудительный TILEMODE откатан (к тому
;;;        же setvar «TILEMODE» капризничает после снятия зависшей
;;;        печати). Новое: после предустановки формат читается обратно —
;;;        в консоли видно, применился ли он («предустановка: <имя>» /
;;;        «НЕ ПРИМЕНИЛАСЬ»); молчаливый отказ предустановки — главный
;;;        подозреваемый в паре вопросов «Сохранить изменения...».
;;; v0.23: РАЗГАДКА «ЗАСТРЯВАНИЙ»: хвост «Сохранить изменения параметров
;;;        листа?/Перейти к печати?» — вопросы ветки ЛИСТА; при запуске с
;;;        вкладки листа лента шла по неверной ветке. На время экспорта
;;;        принудительно TILEMODE=1 (рамки СПДС лежат в модели), вкладка
;;;        восстанавливается после печати. Из ветки листа удалён фантомный
;;;        ответ «не печатать лист последним». Эхо печати: отдельные
;;;        команды ПСПЭХОВКЛ / ПСПЭХОВЫКЛ (PSPECHOON / PSPECHOOFF).
;;;        Двойной учёт пропусков устранён.
;;; v0.22: прогоны без «Печатная область чертежа: ...» = -ПЕЧАТЬ
;;;        спотыкается ДО шага окна; вопрос скрыт CMDECHO=0. Новый
;;;        диагностический режим ПСПЭХО / PSPECHO: не глушит эхо —
;;;        в консоли виден весь транскрипт вопросов и ответов.
;;;        Пропуск не учитывается дважды (было 8 вместо 4).
;;; v0.21: ответ «Д» (Да) не распознавался: getkword с двуязычным
;;;        initget вернул не форму «Да», а иную форму ключа. Сравнение
;;;        заменено на список принимаемых: Да/Yes без учета регистра.
;;; v0.20: автоискатель Ghostscript смотрит и в gs\\bin\\ рядом с
;;;        чертежом (стандартная раскладка установки/архива).
;;; v0.19: СБОРКА В ОДИН МНОГОСТРАНИЧНЫЙ PDF. Если напечатано больше
;;;        одного листа и найден Ghostscript (*psp-gs* -> gs рядом с
;;;        чертежом -> реестр -> Program Files), предлагается «Собрать
;;;        все листы в один PDF? [Да/Нет] <Да>»: L01...LNN склеиваются
;;;        в SPDS_<дата>_<время>.pdf рядом с подпапкой. Без GS —
;;;        подсказка, постраничные PDF остаются.
;;; v0.18: прогон 0.17: пара «Сохранить изменения параметров листа?»/
;;;        «Перейти к печати?» вклинилась в ленту (в прогоне 4/4 была
;;;        подавлена PAPERUPDATE=0) — лента сдвинулась, все листы ушли
;;;        в «_As». Добавлены: печать фактических PAPERUPDATE/
;;;        BACKGROUNDPLOT перед циклом (видно, принялся ли 0); после
;;;        каждой печати проверка CMDACTIVE — застрявший вопрос
;;;        снимается по ESC (psp-clear-stuck), лист помечается
;;;        пропущенным, каскад сдвига невозможен.
;;; v0.17: по выбору пользователя имена файлов: L01.pdf, L02.pdf...
;;;        (префикс L + номер листа; дубликаты номера: L01_2, L01_3).
;;; v0.16: прогон 4/4 без вопросов (PAPERUPDATE=0 подтвердился в свежем
;;;        чертеже, порядок по листам верный, обе ориентации, упрощённая
;;;        рамка с 22 полями тоже прошла). Отладочные контрольные точки
;;;        [1]-[6] удалены; структура с разнесёнными setq сохранена.
;;; v0.15: первый прогон ЭКССПДСВПДФ прошёл, но свежий чертёж задавал
;;;        два вопроса («Сохранить изменения параметров листа?»,
;;;        «Перейти к печати?») — пара PAPERUPDATE; лента сдвигалась и
;;;        файл уходил с посторонним именем. На время экспорта
;;;        PAPERUPDATE=0 (подавить), после — восстановление. Если PDF не
;;;        найден после печати, печатается ожидаемый путь.
;;; v0.14: ПРИЧИНА «stringp T» НАЙДЕНА И ИСПРАВЛЕНА: булевы поля СПДС
;;;        (группа 290) entget отдаёт как T/nil; разбор оставлял такое
;;;        значение как есть, и (atoi T) падал. Разбор 300/40/90/290 теперь
;;;        понимает T->"1", nil->"0" и всё прочее через vl-princ-to-string;
;;;        кратность в экспорте читается со страховкой типа.
;;; v0.13: трассировка локализовала сбой: между «выбрано объектов» и
;;;        сортировкой (цикл сбора). Добавлены контрольные точки [1]-[6]
;;;        по шагам цикла: ssname -> vla-объект -> поля entget -> формат/
;;;        лист -> габариты -> сбор позиции. Последняя напечатанная точка
;;;        укажет оператор, вызывающий «stringp T».
;;; v0.12: по логу первого прогона ЭКССПДСВПДФ: необнаруженная ошибка
;;;        «неверный тип аргумента: stringp T» — добавлена поэтапная
;;;        трассировка печати (объектов/сортировка/папка/каждый лист),
;;;        psp-page-preset обёрнут в vl-catch-all-apply, psp-output-dir
;;;        переживает пустой TEMP. Ошибка диага (тройки вместо строк)
;;;        исправлена в PlotSPDSDiag 0.12.
;;; v0.11: СВОЙСТВА СПДС НАЙДЕНЫ: в entget объекта парами (301 "ключ")
;;;        (300 "значение"): Format, Sheet, SheetCount, Designation,
;;;        Orientation, Multiplicity (журнал 0.10). Новый psp-spds-fields;
;;;        формат/лист/листов в ЭКССПДСВПДФ и диагностике читаются из
;;;        entget (COM-свойства остались запасным каналом). Экстрактор
;;;        собирает пары 301/300 (строки вида "Format: A4"). Кратность
;;;        Multiplicity>1 даёт бумагу на N-1 шагов вверх (как "ФорматXN").
;;; v0.9: ПРИЧИНА СБОЕВ ЗАГРУЗКИ НАЙДЕНА. (load) в AutoCAD не читает
;;;        .lsp дальше ~36 Кбайт (36864 = 0x9000): v0.1-v0.4 (до 36433
;;;        байт) грузились, все версии с v0.5 (45317+) падали с «синтак-
;;;        сической ошибкой» на форме, содержащей этот байт. Диагностика
;;;        вынесена в PlotSPDSDiag.lsp; оба файла теперь меньше предела.
;;;
;;; Этапы разработки:
;;;   0. Диагностика — ЭКССПДСДИАГ: типы объектов, свойства, дамп.
;;;   1. Серийная печать — ЭКССПДСВПДФ: сортировка по «листу»,
;;;      бумага на шаг вверх (A4->A3, A3->A2 ...), файлы s01.pdf ...
;;;   2. Сборка в один многостраничный PDF — следующий этап.

(vl-load-com)

(setq *psp-ver* "0.85")

(setq *psp-open-mode* "rundll")
(setq *psp-open-delay* 300)
(setq *psp-unit-scale* 1.0)
(setq *psp-subdir* "PlotFramePDF")
(setq *psp-color-mode* nil)
(setq *psp-ctb-mono* "monochrome.ctb")
(setq *psp-ctb-color* "acad.ctb")
(setq *psp-output-dir* nil)
;; Путь к Ghostscript (gswin64c.exe); nil — искать автоматически.
;; Команда ПСПГС задаёт путь вручную и запоминает его (setcfg).
(setq *psp-gs* (getcfg "AppData/PlotSPDS/GS"))
(if (= *psp-gs* "") (setq *psp-gs* nil))

;; Имя примитива СПДС и каналы чтения свойств (порядок = приоритет)
(setq *psp-spds-entity* "SPDSFORMAT")

;; Разделы помечены маркерами загрузки (ПСП: секция N/10)
(setq *psp-spds-props-format*
      '("Format" "Формат" "SheetFormat" "FrameFormat" "FormatName"))
(setq *psp-spds-props-sheet*
      '("Sheet" "Лист" "SheetNo" "SheetNumber" "Номер"))
(setq *psp-spds-props-total*
      '("Sheets" "Листов" "SheetsTotal" "TotalSheets"))

;; Таблица форматов (как в PlotFrameToPDF + строка A4)
;; (короткое W_L H_L "портрет" "альбом")
(setq *psp-formats*
  '(("A4"  297  210
     "ISO_full_bleed_A4_(210.00_x_297.00_MM)"
     "ISO_full_bleed_A4_(297.00_x_210.00_MM)")
    ("A3"  420  297
     "ISO_full_bleed_A3_(297.00_x_420.00_MM)"
     "ISO_full_bleed_A3_(420.00_x_297.00_MM)")
    ("A2"  594  420
     "ISO_full_bleed_A2_(420.00_x_594.00_MM)"
     "ISO_full_bleed_A2_(594.00_x_420.00_MM)")
    ("A1"  841  594
     "ISO_full_bleed_A1_(594.00_x_841.00_MM)"
     "ISO_full_bleed_A1_(841.00_x_594.00_MM)")
    ("A0"  1189 841
     "ISO_full_bleed_A0_(841.00_x_1189.00_MM)"
     "ISO_full_bleed_A0_(1189.00_x_841.00_MM)")
    ("2A0" 1682 1189
     "ISO_full_bleed_2A0_(1189.00_x_1682.00_MM)"
     "ISO_full_bleed_2A0_(1682.00_x_1189.00_MM)")
    ("4A0" 2378 1682
     "ISO_full_bleed_4A0_(1682.00_x_2378.00_MM)"
     "ISO_full_bleed_4A0_(2378.00_x_1682.00_MM)")))

;; Сохранённые устройство/формат активного листа (на время печати)
(setq *psp-page-saved* nil)
;; Метка этапа — попадает в сообщение об ошибке
(setq *psp-stage* "-")
;; T: не глушить CMDECHO при печати — видно все подсказки -ПЕЧАТЬ
;; (переключается командой ПСПЭХО / PSPECHO)
(setq *psp-plot-echo* nil)
;; T: в ленту -ПЕЧАТЬ добавляется ответ «_N» для вопроса
;; «Масштабировать веса линий?» (переключается командой ПСПЛЕНТА)
(setq *psp-tape-mode* nil)
;; Настройки (окно — команда ПСПНАСТРОЙКИ / PSPSET; хранение setcfg)
(setq *psp-pdf-dir* "")      ; папка сохранения PDF ("" = temp)
(setq *psp-auto-merge-n* 3)  ; автосборка при листах БОЛЬШЕ этого числа
(setq *psp-open-delay-s* 5)  ; задержка открытия результата, секунд
(setq *psp-open-res* T)      ; открывать результат (склейку/одиночные)
(setq *psp-del-singles* T)   ; удалять одиночные листы после склейки
;; Качество печати: 0 = формат в формат, 1 = +1 формат (как всегда),
;; 2 = +2 формата. Выбор — ПСПКАЧ / PSPQUAL и строка в ПСПНАСТРОЙКИ
(setq *psp-quality* 1)
;; Имя PDF-принтера. В DWG To PDF.pc3 может быть включено «Показывать
;; результаты в программе просмотра» — тогда AutoCAD САМ открывает
;; каждый отпечатанный лист (вкладки просмотрщика, блокировка
;; удаления). Один раз сделайте «тихую» копию принтера без этой
;; галочки (как — команда ПСППОМОЩЬ) и укажите её имя здесь или
;; (setq *psp-pc3* "Имя.pc3") ПОСЛЕ загрузки модуля.
(setq *psp-pc3* "PlotSPDSToPDF.pc3")

;; Восстановление настроек из реестра (записывает ПСПНАСТРОЙКИ)
(defun psp-load-cfg ( / s n)
  (setq s (getcfg "AppData/PlotSPDS/PDFDir"))
  (if (and (= (type s) 'STR) (/= s ""))
    (setq *psp-pdf-dir* s *psp-output-dir* s))
  ;; Параметры печати (задача 12): подхват в ОБА модуля
  ;; (СПДС печатает по *psp-*, база — по *pfp-*)
  (setq s (getcfg "AppData/PlotFrame/ColorMode"))
  (if (= (type s) 'STR)
    (setq *pfp-color-mode* (= s "1") *psp-color-mode* (= s "1")))
  (setq s (getcfg "AppData/PlotFrame/CtbMono"))
  (if (and (= (type s) 'STR) (/= s ""))
    (setq *pfp-ctb-mono* s *psp-ctb-mono* s))
  (setq s (getcfg "AppData/PlotFrame/CtbColor"))
  (if (and (= (type s) 'STR) (/= s ""))
    (setq *pfp-ctb-color* s *psp-ctb-color* s))
  (setq s nil n (getcfg "AppData/PlotSPDS/AutoMergeN"))
  (if (= (type n) 'STR) (setq s (atoi n)))
  (if (and (numberp s) (> s 0)) (setq *psp-auto-merge-n* s))
  (setq s nil n (getcfg "AppData/PlotSPDS/OpenDelay"))
  (if (= (type n) 'STR) (setq s (atoi n)))
  (if (and (numberp s) (>= s 0)) (setq *psp-open-delay-s* s))
  (setq s (getcfg "AppData/PlotSPDS/OpenRes"))
  (cond ((= s "1") (setq *psp-open-res* T))
        ((= s "0") (setq *psp-open-res* nil)))
  (setq s (getcfg "AppData/PlotSPDS/DelSingles"))
  (cond ((= s "1") (setq *psp-del-singles* T))
        ((= s "0") (setq *psp-del-singles* nil)))
  (setq s (getcfg "AppData/PlotSPDS/PC3"))
  (if (and (= (type s) 'STR) (/= s "")
           (wcmatch (strcase s T) "*`.pc3"))
    (setq *psp-pc3* s))
  (setq s nil n (getcfg "AppData/PlotSPDS/Quality"))
  (if (= (type n) 'STR) (setq s (atoi n)))
  (if (and (numberp s) (>= s 0) (<= s 2)) (setq *psp-quality* s))
  (princ))
(psp-load-cfg)

;; ---------------------------------------------------------------------------
;; Утилиты

;; ---------------------------------------------------------------------------

(defun psp-get (obj prop)
  (vl-catch-all-apply 'vlax-get-property (list obj prop)))

(defun psp-safe-put (obj prop val)
  (not (vl-catch-all-error-p
         (vl-catch-all-apply 'vlax-put-property (list obj prop val)))))

;; variant -> значение; safearray/прочее -> как есть; nil при ошибке.
(defun psp-va->list-unwrap (x / v)
  (cond
    ((null x) nil)
    ((= (type x) 'VARIANT)
     (setq v (vl-catch-all-apply 'vlax-variant-value (list x)))
     (if (vl-catch-all-error-p v) nil v))
    (t x)))

(defun psp-pad-right (s width / n)
  (setq n (- width (strlen s)))
  (while (> n 0) (setq s (strcat s " ") n (1- n))) s)

(defun psp-default-dir ()
  (strcat (getenv "TEMP") "\\" *psp-subdir*))

(defun psp-output-dir ( / d)
  (if (null *psp-output-dir*)
    (progn
      (setq d (getenv "TEMP"))
      (if (null d) (setq d (getvar "TEMP")))
      (if (null d) (setq d "C:"))
      (setq d (strcat d "\\" *psp-subdir*))
      (vl-mkdir d)
      (setq *psp-output-dir* d)))
  *psp-output-dir*)

(defun psp-clear-stuck ( / doc i)
  (setq doc (vl-catch-all-apply 'vla-get-ActiveDocument
                                (list (vlax-get-acad-object))))
  (setq i 0)
  (while (and (< i 5) (> (getvar "CMDACTIVE") 0))
    (vl-catch-all-apply 'vla-SendCommand (list doc (chr 27)))
    (setq i (1+ i)))
  (princ))

(defun psp-sleep (ms / old-cmdecho)
  (setq old-cmdecho (getvar "CMDECHO"))
  (setvar "CMDECHO" 0)
  (command "_.delay" ms)
  (setvar "CMDECHO" old-cmdecho))

(defun psp-open-rundll (path / args)
  (setq args (strcat "url.dll,FileProtocolHandler \"" path "\""))
  (startapp "rundll32.exe" args))

(defun psp-open (path)
  (if (= *psp-open-mode* "rundll")
    (psp-open-rundll path)
    (startapp "explorer.exe" path)))

;; Предустановка устройства и формата активного листа через ActiveX:

;; -ПЕЧАТЬ не вставляет лишний вопрос о неподдерживаемом формате.
;; Прежние значения -> *psp-page-saved* -> psp-page-restore.
(defun psp-page-preset (media-name / doc layout cfg med)
  (setq *psp-page-saved* nil)
  (setq doc (psp-get (vlax-get-acad-object) 'ActiveDocument))
  (setq layout (psp-get doc 'ActiveLayout))
  (if (or (null layout) (vl-catch-all-error-p layout))
    nil
    (progn
      (setq cfg (psp-get layout 'ConfigName)
            med (psp-get layout 'CanonicalMediaName))
      (setq *psp-page-saved*
            (list (if (vl-catch-all-error-p cfg) nil cfg)
                  (if (vl-catch-all-error-p med) nil med)))
      (psp-safe-put layout 'ConfigName *psp-pc3*)
      (psp-safe-put layout 'CanonicalMediaName media-name)
      ;; Читаем ФАКТИЧЕСКИ принявшийся формат: лист/устройство могут
      ;; отвергнуть имя (например, альбомный канонический на Листе).
      ;; Лента сверяется с фактом (см. psp-plot-tape).
      (setq med (psp-get layout 'CanonicalMediaName))
      (if (vl-catch-all-error-p med) nil med))))

(defun psp-page-restore ( / doc layout)
  (if *psp-page-saved*
    (progn
      (setq doc (psp-get (vlax-get-acad-object) 'ActiveDocument))
      (setq layout (psp-get doc 'ActiveLayout))
      (if (and (not (null layout)) (not (vl-catch-all-error-p layout)))
        (progn
          (if (car *psp-page-saved*)
            (psp-safe-put layout 'ConfigName (car *psp-page-saved*)))
          (if (cadr *psp-page-saved*)
            (psp-safe-put layout 'CanonicalMediaName
                          (cadr *psp-page-saved*)))))
      (setq *psp-page-saved* nil)))
  (princ))

;; ---------------------------------------------------------------------------
;; Печать окна через -ПЕЧАТЬ (общая лента ответов, Модель/Лист)

;; ---------------------------------------------------------------------------

;; Наборы вопросов -ПЕЧАТЬ у Модели и Листа различаются: у Модели нет
;; вопросов «лист последним»/«удалять скрытые», но есть «Задать
;; тонирование» (ответ — ключевое слово). Лента собирается по TILEMODE.
(defun psp-plot-tape (fname media-name rot-str ctb x1 y1 x2 y2
                      media-chk alt / tape old-cmdecho)
  (setq old-cmdecho (getvar "CMDECHO"))
  (setvar "CMDECHO" (if *psp-plot-echo* 1 0))
  (setq tape
    (append
      (list "_.-plot"
            "_Y"                     ; подробная настройка
            ""                       ; текущий лист
            *psp-pc3*                ; устройство
            (cond                     ; nil в ленте command недопустим!
              ((= 1 (getvar "TILEMODE")) "") ;Лист: Enter — формат уже
                                       ;предустановлен; лист хранит ПОРТ-
                                       ;РЕТНЫЙ канон, шлём Enter, а не план
              ((= (type media-chk) 'STR) media-chk) ;Модель: факт преду-
                                       ;становки (обычно совпадает с планом)
              (t media-name))
            "_M"                     ; мм
            rot-str                  ; ориентация _L / _P
            "_N"                     ; не переворачивать
            "_W"                     ; область: Рамка
            (list x1 y1)             ; нижний левый угол
            (list x2 y2)             ; верхний правый угол
            "_F"                     ; вписать
            "_C"                     ; центрировать
            "_Y"                     ; учитывать стили печати
            ctb                      ; CTB-файл
            "_Y")                    ; учитывать веса линий
      ;; В части сборок AutoCAD есть вопрос «Масштабировать веса линий?»,
      ;; в части (см. транскрипт 0.24) его нет. По умолчанию НЕТ (лишний
      ;; ответ сдвигал ленту: имя файла получало "_As"). Переключение:
      ;; ПСПЛЕНТА / PSPTAPE.
      (if (= 1 (getvar "TILEMODE"))
        ;; --- вкладка Модель ---
        (append
          (if *psp-tape-mode*        ; «Масштабировать веса?» задаёт не
            (list "_N"))             ; каждая сборка (см. ПСПЛЕНТА)
          (list
            "_As"                    ; тонирование: по отображению
            fname                    ; имя файла
            "_N"                     ; не сохранять в параметры
            "_Y"))                   ; печатать
        ;; --- вкладка Лист ---
        ;; Три «Нет» (масштабировать веса / печатать лист первым /
        ;; скрывать объекты листа). Вопрос «записать изменения в
        ;; макет» появляется ТОЛЬКО когда настройки печати отлича-
        ;; ются от сохранённых в листе, поэтому постоянного ответа
        ;; под него нет: второй заход (alt) шлёт четвёртое «Нет».
        (append
          (list "_N" "_N" "_N")
          (if alt (list "_N"))
          (list fname "_N" "_Y")))))
  (apply 'command tape)
  (setvar "CMDECHO" old-cmdecho)
  t)

;; ---------------------------------------------------------------------------
;; СПДС: чтение свойств и геометрии

;; ---------------------------------------------------------------------------

;; Чтение свойства по списку имён-кандидатов.
;; Возвращает (значение имя_канала) или nil. Значение -> строка.
(defun psp-spds-prop-ex (obj names / nm avail v val)
  (setq val nil)
  (while (and names (null val))
    (setq nm (car names)
          avail (vl-catch-all-apply 'vlax-property-available-p
                                    (list obj nm T)))
    (if (and (not (vl-catch-all-error-p avail)) avail)
      (progn
        (setq v (psp-get obj nm))
        (if (not (vl-catch-all-error-p v))
          (progn
            (setq val (psp-va->list-unwrap v))
            (if (not (null val))
              (setq val (cond
                          ((= (type val) 'STR) (if (= val "") nil val))
                          ((= (type val) 'INT) (itoa val))
                          ((= (type val) 'REAL) (itoa (fix val)))
                          (t (vl-princ-to-string val)))))))))
    (if (null val) (setq names (cdr names))))
  (if val (list val nm) nil))

(defun psp-spds-prop (obj names / r)
  (setq r (psp-spds-prop-ex obj names))
  (if r (car r) nil))

;; Значение hex-символа (0-9, A-F, a-f) или nil.
(defun psp-hexval (ch / c)
  (setq c (ascii ch))
  (cond
    ((and (>= c 48) (<= c 57)) (- c 48))
    ((and (>= c 65) (<= c 70)) (- c 55))
    ((and (>= c 97) (<= c 102)) (- c 87))
    (t nil)))

;; Строка hex-пар -> байтовая строка. Некорректные хвосты игнорируются.
(defun psp-hex->str (hex / i h1 h2 res)
  (setq i 1 res "")
  (if hex
    (progn
      (while (<= (+ i 1) (strlen hex))
        (setq h1 (psp-hexval (substr hex i 1))
              h2 (psp-hexval (substr hex (1+ i) 1)))
        (if (and h1 h2)
          (setq res (strcat res (chr (+ (* 16 h1) h2)))))
        (setq i (+ i 2)))))
  res)

;; Читаемые фрагменты (печатаемые коды 32..255) длиной >= minlen.
(defun psp-printable-runs (s minlen / i code run res)
  (setq i 1 run "" res nil)
  (if s
    (progn
      (while (<= i (strlen s))
        (setq code (ascii (substr s i 1)))
        (if (and (>= code 32) (/= code 127) (<= code 255))
          (setq run (strcat run (substr s i 1)))
          (progn
            (if (>= (strlen run) minlen) (setq res (cons run res)))
            (setq run "")))
        (setq i (1+ i)))
      (if (>= (strlen run) minlen) (setq res (cons run res)))))
  (reverse res))

;; Объединение строк через разделитель.
(defun psp-join (sep lst / res)
  (setq res "")
  (foreach s lst
    (setq res (if (= res "") s (strcat res sep s))))
  res)

;; Строки объекта СПДС: entget (группы 1, 3 и бинарные 310-312),
;; XRecord'ы расширения словаря, XData. Каждый шаг защищён.
(defun psp-spds-strings (obj ent / ed item runs s res dict it nm k301
                             codes vals cl vl i v)
  (setq res nil)
  ;; 1) entget: тексты, бинарные данные, XData (группы 1000+;
  ;;    entget с '("*") возвращает XData всех приложений)
  (setq ed (vl-catch-all-apply 'entget (list ent '("*"))))
  (if (and (not (vl-catch-all-error-p ed)) ed)
    (foreach item ed
      (cond
        ((and (= (car item) 301) (= (type (cdr item)) 'STR))
         (setq k301 (cdr item)))
        ((and k301 (member (car item) '(300 40 90 290)))
         (setq v (cdr item)
               v (cond ((= (type v) 'STR) v)
                       ((= (type v) 'INT) (itoa v))
                       ((= (type v) 'REAL) (rtos v 2 2))
                       ((eq v T) "1")
                       ((null v) "0")
                       (t (vl-princ-to-string v))))
         (setq res (cons (strcat k301 ": " v) res)
               k301 nil))
        ((and (member (car item) '(1 3))
              (= (type (cdr item)) 'STR)
              (> (strlen (cdr item)) 1))
         (setq res (cons (cdr item) res)))
        ((and (member (car item) '(310 311 312))
              (= (type (cdr item)) 'STR))
         (setq runs (psp-printable-runs (psp-hex->str (cdr item)) 4))
         (foreach s runs (setq res (cons s res))))
        ((and (= (car item) 1000) (= (type (cdr item)) 'STR)
              (> (strlen (cdr item)) 1))
         (setq res (cons (cdr item) res)))
        ((and (= (car item) 1004) (= (type (cdr item)) 'STR))
         (setq runs (psp-printable-runs (psp-hex->str (cdr item)) 4))
         (foreach s runs (setq res (cons s res))))
        ((and (>= (car item) 1010) (<= (car item) 1071))
         (setq res (cons (strcat "XD[" (itoa (car item)) "]="
                                 (vl-princ-to-string (cdr item)))
                         res))))))
  ;; 2) расширение словаря: XRecord'ы
  (setq dict (vl-catch-all-apply 'vla-getextensiondictionary
                                 (list obj)))
  (if (and (not (vl-catch-all-error-p dict)) dict)
    (vlax-for it dict
      (setq nm (psp-get it 'ObjectName))
      (if (and (not (vl-catch-all-error-p nm)) (= nm "AcDbXrecord"))
        (progn
          (setq codes nil vals nil)
          (vl-catch-all-apply 'vla-getxrecorddata (list it 'codes 'vals))
          (if (and codes (not (vl-catch-all-error-p codes)))
            (progn
              (setq codes (vl-catch-all-apply 'vlax-safearray->list
                              (list (psp-va->list-unwrap codes))))
              (if (vl-catch-all-error-p codes) (setq codes nil))))
          (if (and vals (not (vl-catch-all-error-p vals)))
            (progn
              (setq vals (vl-catch-all-apply 'vlax-safearray->list
                              (list (psp-va->list-unwrap vals))))
              (if (vl-catch-all-error-p vals) (setq vals nil))))
          (if (and codes vals)
            (progn
              (setq i 0)
              (while (and (< i (length codes))
                          (< i (length vals)))
                (setq v (psp-va->list-unwrap (nth i vals)))
                (if (= (type v) 'SAFEARRAY)
                  (setq v (vl-catch-all-apply 'vlax-safearray->list
                              (list v))))
                (if (vl-catch-all-error-p v) (setq v nil))
                (if (and v (= (type v) 'LIST))
                  (setq v (psp-join " " (mapcar 'vl-princ-to-string v))))
                (if v
                  (setq res (cons (strcat "XR[" (itoa (nth i codes))
                                          "]=" (vl-princ-to-string v))
                                  res)))
                (setq i (1+ i)))))))))
  (reverse res))

;; Замена кириллических гомоглифов на латиницу (остальные символы
;; не трогаются — позиции сохраняются).
(defun psp-spds-latinize (s / i ch res)
  (setq i 1 res "")
  (while (<= i (strlen s))
    (setq ch (substr s i 1)
          res (strcat res
                (cond
                  ((member ch '("А" "A")) "A")
                  ((member ch '("В" "B")) "B")
                  ((member ch '("С" "C")) "C")
                  ((member ch '("Е" "E")) "E")
                  ((member ch '("Н" "H")) "H")
                  ((member ch '("К" "K")) "K")
                  ((member ch '("М" "M")) "M")
                  ((member ch '("О" "O")) "O")
                  ((member ch '("Р" "P")) "P")
                  ((member ch '("Т" "T")) "T")
                  ((member ch '("У" "Y")) "Y")
                  ((member ch '("Х" "X")) "X")
                  (t ch)))
          i (1+ i)))
  res)

;; Кандидаты формата в строках: A1..A5 (латиница/кириллица),
;; 2A0/4A0; кратность вида A4X2/A4Х2 тоже отмечается.
(defun psp-spds-candidates (strs / res s su i ch n1 n2 tok)
  (foreach s strs
    (setq su (psp-spds-latinize (strcase s)) i 1)
    (while (<= i (strlen su))
      (setq ch (substr su i 1))
      (cond
        ;; 2A0 / 4A0
        ((and (member ch '("2" "4"))
              (<= (+ i 2) (strlen su))
              (member (substr su (1+ i) 1) '("A"))
              (= (substr su (+ i 2) 1) "0"))
         (setq tok (strcat ch "A0"))
         (if (not (member tok res)) (setq res (cons tok res)))
         (setq i (+ i 2)))
        ;; A0..A5 (в т.ч. с кратностью A4X3)
        ((member ch '("A"))
         (setq n1 (if (<= (1+ i) (strlen su))
                    (substr su (1+ i) 1) ""))
         (if (and (>= (ascii n1) 48) (<= (ascii n1) 53))
           (progn
             (setq tok (strcat ch n1)
                   n2 (if (<= (+ i 2) (strlen su))
                        (substr su (+ i 2) 1) ""))
             (if (and (member n2 '("X"))
                      (<= (+ i 3) (strlen su))
                      (>= (ascii (substr su (+ i 3) 1)) 49)
                      (<= (ascii (substr su (+ i 3) 1)) 57))
               (setq tok (strcat tok "X" (substr su (+ i 3) 1))))
             (if (not (member tok res)) (setq res (cons tok res))))))
        (t nil))
      (setq i (1+ i))))
  (reverse res))

;; Свойства строки диагностики: (формат-имя лист листов габариты).
;; Пары (301 "ключ") (300 "значение") в entget SPDSFORMAT: Format, Sheet,
;; SheetCount, Designation, Orientation, Multiplicity, Name, Info и т.д.
(defun psp-spds-fields (ent / ed item key val res)
  (setq ed (entget ent) res nil key nil)
  (foreach item ed
    (cond
      ((and (= (car item) 301) (= (type (cdr item)) 'STR))
       (setq key (cdr item)))
      ((and key (member (car item) '(300 40 90 290)))
       (setq val (cdr item)
             val (cond ((= (type val) 'STR) val)
                       ((= (type val) 'INT) (itoa val))
                       ((= (type val) 'REAL) (rtos val 2 2))
                       ((eq val T) "1")
                       ((null val) "0")
                       (t (vl-princ-to-string val))))
       (setq res (cons (cons key val) res) key nil))))
  (reverse res))

(defun psp-field (fields name / p)
  (setq p (assoc name fields))
  (if p (cdr p)))

(defun psp-spds-row (obj / ent f)
  (setq ent (vlax-vla-object->ename obj)
        f (psp-spds-fields ent))
  (list (if (psp-field f "Format")
          (list (psp-field f "Format") "entget301")
          (psp-spds-prop-ex obj *psp-spds-props-format*))
        (if (psp-field f "Sheet")
          (list (psp-field f "Sheet") "entget301")
          (psp-spds-prop-ex obj *psp-spds-props-sheet*))
        (if (psp-field f "SheetCount")
          (list (psp-field f "SheetCount") "entget301")
          (psp-spds-prop-ex obj *psp-spds-props-total*))
        (psp-spds-bbox obj)))

;; Габариты объекта в WCS: (llx lly urx ury) или nil.

;; GetBoundingBox через vl-catch-all-apply привязывает к символам
;; safearray (иногда variant) — оба варианта разбирает psp-va->list-unwrap.
(defun psp-spds-bbox (obj / mn mx a b)
  (vl-catch-all-apply 'vla-getboundingbox (list obj 'mn 'mx))
  (if (and (boundp 'mn) (boundp 'mx))
    (progn
      (setq a (vl-catch-all-apply 'vlax-safearray->list
                                  (list (psp-va->list-unwrap mn)))
            b (vl-catch-all-apply 'vlax-safearray->list
                                  (list (psp-va->list-unwrap mx))))
      (if (and (not (vl-catch-all-error-p a))
               (not (vl-catch-all-error-p b))
               a b (= (length a) 3) (= (length b) 3))
        (list (car a) (cadr a) (car b) (cadr b))
        nil))
    nil))

;; Нормализация имени формата: верхний регистр, кириллические
;; гомоглифы -> латиница. "А4х3" -> "A4X3".
(defun psp-spds-norm (s / i ch res)
  (setq s (strcase (vl-string-trim " \\t" s)) res "" i 1)
  (while (<= i (strlen s))
    (setq ch (substr s i 1)
          res (strcat res
                (cond
                  ((member ch '("А" "A")) "A")
                  ((member ch '("В" "B")) "B")
                  ((member ch '("С" "C")) "C")
                  ((member ch '("Е" "E")) "E")
                  ((member ch '("Н" "H")) "H")
                  ((member ch '("К" "K")) "K")
                  ((member ch '("М" "M")) "M")
                  ((member ch '("О" "O")) "O")
                  ((member ch '("Р" "P")) "P")
                  ((member ch '("Т" "T")) "T")
                  ((member ch '("У" "Y")) "Y")
                  ((member ch '("Х" "X")) "X")
                  ((member ch '("0" "1" "2" "3" "4"
                                 "5" "6" "7" "8" "9")) ch)
                  (t "")))
          i (1+ i)))
  res)

;; Разбор нормализованного имени: "A4X3" -> ("A4" 3); "2A0" -> ("2A0" 1).
;; База — буквы и цифры до разделителя X; после X — кратность.
(defun psp-spds-parse (norm / k base mult)
  (cond
    ((or (null norm) (= norm "")) nil)
    ((and (setq k (vl-string-search "X" norm)) (> k 0))
     (setq base (substr norm 1 k)
           mult (atoi (substr norm (+ k 2))))
     (if (> mult 0) (list base mult) (list base 1)))
    (t (list norm 1))))

;; Индекс номинала в таблице форматов (по короткому имени).
(defun psp-format-idx (base / i lst found)
  (setq i 0 lst *psp-formats* found nil)
  (while (and lst (not found))
    (if (equal (nth 0 (car lst)) base) (setq found i))
    (setq i (1+ i) lst (cdr lst)))
  found)

;; Бумага «на шаг вверх» по номиналу: A4->A3, A3->A2 ... 4A0->4A0.
;; Возвращает запись *psp-formats* или nil.
(defun psp-spds-size-up (base / idx n)
  (setq idx (psp-format-idx base)
        n (length *psp-formats*))
  (cond
    ((null idx) nil)
    ((>= idx (1- n)) (nth (1- n) *psp-formats*))
    (t (nth (1+ idx) *psp-formats*))))

;; Поиск Ghostscript: переменная *psp-gs* -> портативный gs рядом
;; с чертежом -> реестр -> Program Files. Возвращает путь к консольному
;; gswin64c.exe/gswin32c.exe или nil.
;; Каталог файла: всё до последнего "\\" (вручную, без vl-filename-*:
;; на машине с СПДС хуками vl-filename-directory возвращает T)
(defun psp-file-dir (path / i last)
  (setq i 1 last 0)
  (if (= (type path) 'STR)
    (progn
      (while (<= i (strlen path))
        (if (= (substr path i 1) "\\") (setq last i))
        (setq i (1+ i)))
      (if (> last 0) (substr path 1 (1- last)) ""))))

;; Имя файла без каталога: всё после последнего "\\"
(defun psp-file-base (path / i last)
  (setq i 1 last 0)
  (if (= (type path) 'STR)
    (progn
      (while (<= i (strlen path))
        (if (= (substr path i 1) "\\") (setq last i))
        (setq i (1+ i)))
      (if (> last 0) (substr path (1+ last)) path))))

;; Поиск Ghostscript: переменная *psp-gs* -> gs рядом с чертежом ->
;; реестр (GS_DLL/GS_LIB) -> Program Files. Каждый этап печатает
;; результат (диагностика «gs=T»); наружу только строка или nil.
;; Поиск Ghostscript. Приоритет: явный путь (ПСПГС) -> реестр
;; (GS_DLL/GS_LIB = фактический каталог установки) -> Program Files ->
;; портативный в папке модулей -> пути рядом с чертежом (на веру,
;; последними). Проверок файлов нет (на машине с СПДС findfile/open
;; возвращают T), КРОМЕ портативной ветки: диск выбирается по факту
;; существования папки (vl-file-directory-p — проверен чисто).
(defun psp-find-gs ( / try res brand vk v pd sub exe p)
  (defun try (p)
    (if (= (type p) 'STR) p nil))
  ;; 1) явно задан командой ПСПГС (запоминается в реестре настроек)
  (setq res (try *psp-gs*))
  (if res (princ (strcat "\n  GS[1] задан ПСПГС: " res)))
  ;; 2) реестр: каталог установки из GS_DLL/GS_LIB
  (if (null res)
    (foreach brand (list "GPL Ghostscript" "AFPL Ghostscript" "GNU Ghostscript")
      (if (null res)
        (foreach vk (vl-registry-descendents
                      (strcat "HKEY_LOCAL_MACHINE\\SOFTWARE\\" brand))
          (if (null res)
            (foreach vn (list "GS_DLL" "GS_LIB")
              (if (null res)
                (progn
                  (setq v (vl-registry-read
                            (strcat "HKEY_LOCAL_MACHINE\\SOFTWARE\\"
                                    brand "\\" (vl-princ-to-string vk))
                            vn))
                  (if (= (type v) 'STR)
                    (progn
                      (setq res (or (try (strcat (psp-file-dir v)
                                                 "\\gswin64c.exe"))
                                    (try (strcat (psp-file-dir v)
                                                 "\\gswin32c.exe"))))
                      (if res
                        (princ (strcat "\n  GS[2] реестр "
                                       (vl-princ-to-string vk) "\\" vn
                                       ": " res)))))))))))))
  ;; 3) Program Files: gs\\gs<версия>\\bin
  (if (null res)
    (foreach pd (list "C:\\Program Files\\gs" "C:\\Program Files (x86)\\gs")
      (if (vl-file-directory-p pd)
        (foreach sub (vl-directory-files pd nil -1)
          (if (= (type sub) 'STR)
            (foreach exe (list "gswin64c.exe" "gswin32c.exe")
              (if (null res)
                (progn
                  (setq res (try (strcat pd "\\" sub "\\bin\\" exe)))
                  (if res
                    (princ (strcat "\n  GS[3] Program Files: " res)))))))))))
  ;; 3.5) портативный Ghostscript в папке модулей
  ;;      (<диск>:\PlotFrameToPDF\gs\bin\gswin64c.exe): страховая
  ;;      ветка на случай, когда установленного GS нет (реестр и
  ;;      Program Files пусты); диск — первый, где есть папка
  (if (null res)
    (foreach pd (list "C:" "D:" "E:")
      (if (and (null res)
               (vl-file-directory-p
                 (strcat pd "\\PlotFrameToPDF\\gs\\bin")))
        (progn
          (setq res (try (strcat pd "\\PlotFrameToPDF\\gs\\bin\\gswin64c.exe")))
          (if res (princ (strcat "\n  GS[3.5] портативный: " res)))))))

  ;; 4) рядом с чертежом (пути «на веру»: существуют, только если
  ;;    GS туда действительно клали)
  (if (null res)
    (foreach p (list (strcat (getvar "DWGPREFIX") "gs\\bin\\gswin64c.exe")
                     (strcat (getvar "DWGPREFIX") "gs\\bin\\gswin32c.exe")
                     (strcat (getvar "DWGPREFIX") "gs\\gswin64c.exe")
                     (strcat (getvar "DWGPREFIX") "gs\\gswin32c.exe")
                     (strcat (getvar "DWGPREFIX") "gswin64c.exe")
                     (strcat (getvar "DWGPREFIX") "gswin32c.exe"))
      (if (null res)
        (progn
          (setq res (try p))
          (if res (princ (strcat "\n  GS[4] рядом с чертежом: " res)))))))
  ;; страховка: наружу только строка или nil
  (if (= (type res) 'STR) res nil))

;; Безопасная строка: STR как есть, nil -> "", прочее -> princ-to-string
;; (T и прочие не-строки не роняют strcat). Утеряна срезом 0.32,
;; возвращена в 0.34: во втором чертеже чистое пространство имён
;; показало «no function definition: PSP-S->STR».
(defun psp-s->str (x)
  (cond
    ((= (type x) 'STR) x)
    ((null x) "")
    (t (vl-princ-to-string x))))

;; Только STR, иначе умолчание: T из списков не должен выживать
(defun psp-str-or (v d)
  (if (= (type v) 'STR) v d))

;; Открыть PDF и убрать одиночные листы. Ghostscript создаёт файл
;; выхода СРАЗУ, а закрывает только в конце работы: и открытие, и
;; удаление листов выполняются с задержкой ~5 с (ping) в ОТДЕЛЬНОМ
;; фоновом cmd — AutoCAD не ждёт, gs успевает закрыть файлы.
;; Одиночные листы удаляются ОДНОЙ командой с маской dir\L*.pdf:
;; в папке сборки только листы L*.pdf; альбом называется
;; <имя чертежа>_<дата>_<время>.pdf — под маску L*.pdf не попадает.
;; Цепочка из отдельных del на каждый лист (0.42) не сработала —
;; слишком длинная команда. Запасной путь — explorer (без удаления).
(defun psp-open-pdf (path dir / ok cmd dl)
  (setq dl (itoa (1+ *psp-open-delay-s*)))
  (princ (strcat " (открытие через ~" (itoa *psp-open-delay-s*) " с)"))
  ;; проверка альбома в LISP (в момент фактического открытия):
  ;; нет файла — открывается папка сборки, а не ничего
  (if (findfile (psp-s->str path))
    (progn
      (setq cmd (strcat "ping -n " dl " 127.0.0.1 > nul"))
      (if *psp-del-singles*
        (setq cmd (strcat cmd " & del \"" dir "\\L*.pdf\"")))
      (setq cmd (strcat cmd " & start \"\" \"" path "\""))
      (setq ok (startapp "cmd.exe" (strcat "/c " cmd)))
      (princ (strcat "[cmd=" (psp-s->str ok) "]"))
      (if (null ok)
        (progn
          (setq ok (startapp "explorer.exe" path))
          (princ (strcat "[explorer=" (psp-s->str ok) "]")))))
    (progn
      (princ "\nПСП: альбом не найден — открываю папку сборки.")
      (setq ok (startapp "explorer.exe" dir))
      (princ (strcat "[explorer=" (psp-s->str ok) "]"))))
  ;; Вторая волна: PDF-XChange держит ОТКРЫТЫЕ листы (вкладки), Windows
  ;; не удаляет занятые файлы (подтверждено диагностикой: при закрытом
  ;; просмотрщике del чист, при открытом — ошибки блокировки).
  ;; Повторяем del ~1 минуту (12 x 5 с): листы удалятся, как только
  ;; просмотрщик будет закрыт.
  (if *psp-del-singles*
    (progn
      (princ "\nПСП: листы будут удаляться ещё ~1 мин (если просмотрщик их держал)")
      (startapp "cmd.exe"
                (strcat "/c for /l %i in (1,1,12)"
                        " do @(ping -n " dl " 127.0.0.1 > nul"
                        " & del \"" dir "\\L*.pdf\" 2>nul)"))))
  ok)

(defun psp-merge-pdfs (gs src-lst trg / cmd k s prev cur stable)
  ;; диагностика: размер каждого входа (0 байт = страница выпадет)
  (foreach s src-lst
    (princ (strcat "\n  вход " (psp-s->str s) ": "
                   (if (findfile (psp-s->str s))
                     (strcat (itoa (vl-file-size (psp-s->str s)))
                             " байт")
                     "НЕТ"))))
  (setq cmd (strcat "\"" (psp-s->str gs) "\""
                    " -dBATCH -dNOPAUSE -dSAFER -dQUIET -sDEVICE=pdfwrite"
                    " -sOutputFile=\"" (psp-s->str trg) "\""))
  (foreach s src-lst
    (setq cmd (strcat cmd " \"" (psp-s->str s) "\"")))
  (startapp cmd)
  ;; GS создаёт файл СРАЗУ, а дописывает последним: ждать не появле-
  ;; ния, а СТАБИЛИЗАЦИИ размера (иначе зритель открывал недописан-
  ;; ный альбом — «склеилось 5/6 из 7»)
  (setq k 0 prev -1 cur -1 stable 0)
  (while (and (< stable 3) (< k 60))
    (psp-sleep 500)
    (setq cur (if (findfile trg)
                (vl-file-size (psp-s->str trg)) -1))
    (if (and (> cur 0) (= cur prev))
      (setq stable (1+ stable))
      (setq stable 0))
    (setq prev cur k (1+ k)))
  (if (> cur 0)
    (princ (strcat "\n  размер альбома: " (itoa cur) " байт")))
  (if (> cur 0) trg nil))

;; ---------------------------------------------------------------------------
;; СПДС: сортировка и имена

;; ---------------------------------------------------------------------------

(defun psp-pad2 (n)
  (if (< n 10) (strcat "0" (itoa n)) (itoa n)))

;; Номер листа как число: "15" -> 15.0, "15.1" -> 15.1 (запятая тоже
;; понимается); nil/пустое -> 0 (без номера). Дробные листы (15, 15.1,
;; 15.2) сортируются по возрастанию: 15 < 15.1 < 15.2.
(defun psp-sheet-num (s)
  (if (= (type s) 'STR)
    (atof (vl-string-translate "," "." s))
    0.0))

;; T: строка номера листа — настоящий номер (непустая и состоит
;; только из цифр, точек и запятых). "0" -> T (титульный лист),
;; "15.1" -> T, nil/""/"А" -> nil (лист считается безномерным).
(defun psp-sheet-p (s / i n ch ok)
  (if (= (type s) 'STR)
    (progn
      (setq s (vl-string-trim " " s)
            i 1
            n (strlen s)
            ok (> n 0))
      (while (and ok (<= i n))
        (setq ch (substr s i 1))
        (if (not (or (= ch ".") (= ch ",")
                     (and (>= ch "0") (<= ch "9"))))
          (setq ok nil))
        (setq i (1+ i)))
      ok)
    nil))

;; Имя файла из строки номера СПДС: "15" -> "L15" (целая часть
;; дополняется до двух знаков: "9" -> "L09"), "15.1" -> "L15.1",
;; запятая заменяется точкой.
(defun psp-sheet-name (s / norm k)
  (if (= (type s) 'STR)
    (progn
      (setq norm (vl-string-trim " " (vl-string-translate "," "." s)))
      (if (= norm "")
        nil
        (if (setq k (vl-string-search "." norm))
          (strcat "L" (substr norm 1 k) (substr norm (1+ k)))
          (strcat "L" (psp-pad2 (atoi norm))))))
    nil))

;; Число для отчёта: целое вещественное печатается без ".0"
(defun psp-num-str (n)
  (if (and (= (type n) 'REAL) (= n (float (fix n))))
    (itoa (fix n))
    (vl-princ-to-string n)))

;; Уникальное имя: s01; повторы -> s01_2, s01_3 ...
(defun psp-spds-uniq (base used / nm k)
  (setq nm base k 1)
  (while (member nm used)
    (setq k (1+ k) nm (strcat base "_" (itoa k))))
  (list nm (cons nm used)))

;; Порядок «меньше» для печати: лист по возрастанию; без номера —
;; в конец; внутри — сверху вниз (lly = nth 5, убывает), затем
;; слева направо (llx = nth 4, возрастает).
(defun psp-spds-less (a b)
  (cond
    ((< (nth 3 a) (nth 3 b)) T)
    ((> (nth 3 a) (nth 3 b)) nil)
    ((> (nth 5 a) (nth 5 b)) T)
    ((< (nth 5 a) (nth 5 b)) nil)
    (t (< (nth 4 a) (nth 4 b)))))

;; Сортировка вставкой (списки небольшие).
(defun psp-spds-sorted (items / res it head rest done)
  (setq res nil)
  (foreach it items
    (setq head nil rest res done nil)
    (while (and rest (not done))
      (if (psp-spds-less it (car rest))
        (setq done T)
        (setq head (cons (car rest) head) rest (cdr rest))))
    (setq res (append (reverse head) (list it) rest)))
  res)
;; ---------------------------------------------------------------------------
;; Команда: ЭКССПДСВПДФ / SPDSTOPDF

;; ---------------------------------------------------------------------------

(defun c:ЭКССПДСВПДФ ( / ss n i ent obj it items fmt sheet sheet-i
                          bb used rec media rot-str ctb dir stamp fname
                          nm-n w h x1 y1 x2 y2 ok-list skip j row flds mult multv
                          old-bg old-paper old-trans has-trans res
                          merge-list gs ans merged pdfs k chk auto-merge
                          dwgn)
  (princ "\nЭкспорт форматов СПДС в PDF. Выберите объекты (или All).")
  (setq ss (ssget (list (cons 0 *psp-spds-entity*))))
  (cond
    ((null ss) (princ "\nОтменено.") (princ))
    (t
     ;; Сбор сведений
     (setq n (sslength ss) i 0 items nil skip nil)
     (princ (strcat "\nПСП: выбрано объектов: " (itoa n)))
     (while (< i n)
       (setq ent (ssname ss i))
       (setq obj (vlax-ename->vla-object ent))
       (setq flds (psp-spds-fields ent))
       (setq fmt (psp-field flds "Format"))
       (if (null fmt)
         (setq fmt (psp-spds-prop obj *psp-spds-props-format*)))
       (setq sheet (psp-field flds "Sheet"))
       (if (null sheet)
         (setq sheet (psp-spds-prop obj *psp-spds-props-sheet*)))
       (setq sheet-i (psp-sheet-num sheet))
       (setq bb (psp-spds-bbox obj))
       ;; кратность: A4 + Multiplicity 3 -> "A4X3" (бумага на 3 шага вверх)
       (setq multv (psp-field flds "Multiplicity"))
       (if (/= (type multv) 'STR) (setq multv "1"))
       (setq mult (atoi multv))
       (if (and fmt (> mult 1))
         (setq fmt (strcat fmt "X" (itoa mult))))
       (if bb
         (setq items
               (cons (list ent obj fmt
                           (if (psp-sheet-p sheet) sheet-i 9999.0)
                           (car bb) (cadr bb) (caddr bb) (cadddr bb)
                           sheet)
                     items))
         (setq skip (cons (cdr (assoc 5 (entget ent))) skip)))
       (setq i (1+ i)))
     (setq items (psp-spds-sorted (reverse items)))
     (princ (strcat "\nПСП: к печати после сортировки: " (itoa (length items))))
     (cond
       ((null items)
        (princ "\nУ выбранных объектов нет габаритов — печатать нечего.")
        (princ))
       (t
        ;; Папка сборки: <имя чертежа> (без даты); альбом внутри:
        ;; <имя>_<дата>_<время>.pdf — повторные сборки накапливаются
        ;; в одной папке. (DWGNAME минус расширение; DWGTITLED —
        ;; только флаг 0/1, именем служить не может)
        (setq stamp (rtos (getvar "CDATE") 2 6)
              dwgn (getvar "DWGNAME"))
        (if (/= (type dwgn) 'STR) (setq dwgn ""))
        (setq k (strlen dwgn))
        ;; точка трёхсимвольного расширения — на позиции k-3
        (if (and (> k 4) (= (substr dwgn (- k 3) 1) "."))
          (setq dwgn (substr dwgn 1 (- k 4))))
        (if (= dwgn "") (setq dwgn "SPDS"))
        (setq dir (strcat (psp-output-dir) "\\" dwgn))
        (if (not (vl-file-directory-p dir)) (vl-mkdir dir))
        (princ (strcat "\nПСП: папка сборки: " dir))
        (setq ctb (if *psp-color-mode* *psp-ctb-color* *psp-ctb-mono*))
        ;; Системные переменные: сохранить -> изменить -> восстановить
        (setq has-trans
              (not (vl-catch-all-error-p
                     (vl-catch-all-apply
                       'getvar '("PLOTTRANSPARENCYOVERRIDE")))))
        (if has-trans (setq old-trans (getvar "PLOTTRANSPARENCYOVERRIDE")))
        (setq old-bg (getvar "BACKGROUNDPLOT"))
        (setq old-paper (vl-catch-all-apply 'getvar (list "PAPERUPDATE")))
        (psp-clear-stuck)
        (setvar "BACKGROUNDPLOT" 0)
        ;; 0 = не спрашивать "Сохранить изменения параметров листа?"/
        ;; "Перейти к печати?" при несовпадении размеров (первая печать
        ;; в свежем чертеже без лишних подтверждений)
        (if (not (vl-catch-all-error-p old-paper))
          (setvar "PAPERUPDATE" 0))


        (princ (strcat "\nПСП: PAPERUPDATE="
                       (itoa (getvar "PAPERUPDATE"))
                       " BACKGROUNDPLOT="
                       (itoa (getvar "BACKGROUNDPLOT"))
                       (if *psp-plot-echo* " (эхо=вкл)" " (эхо=выкл)")))
        (if (and (not (vl-catch-all-error-p old-paper))
                 (/= (getvar "PAPERUPDATE") 0))
          (princ "\nПСП: ВНИМАНИЕ: PAPERUPDATE не принят = 0!"))
        (if has-trans (setvar "PLOTTRANSPARENCYOVERRIDE" 1))
        ;; Цикл печати
        (setq used nil ok-list nil j 0)
        (foreach it items
          (setq w (- (nth 6 it) (nth 4 it))
                h (- (nth 7 it) (nth 5 it))
                rec (if (nth 2 it)
                      (car (psp-spds-parse (psp-spds-norm (nth 2 it)))))
                rec (cond
                      ((null rec) nil)
                      ((= *psp-quality* 0)
                       (if (psp-format-idx rec)
                         (nth (psp-format-idx rec) *psp-formats*)
                         nil))
                      ((= *psp-quality* 2)
                       (psp-spds-size-up
                         (nth 0 (psp-spds-size-up rec))))
                      (t (psp-spds-size-up rec)))
                rec (if rec rec (nth 3 *psp-formats*))
                media (if (>= w h) (nth 4 rec) (nth 3 rec))
                rot-str (if (>= w h) "_L" "_P")
                nm-n (psp-spds-uniq
                       (if (nth 8 it)
                         (psp-sheet-name (nth 8 it))
                         (strcat "L" (psp-pad2 (1+ j))))
                       used)
                fname (strcat dir "\\" (car nm-n))
                used (cadr nm-n))
          (princ (strcat "\n  ПСП: " (car nm-n) " (" media ")"))
          ;; Предустановка формата листа (без лишних вопросов)
          (setq *psp-stage* "предустановка листа")
          (setq res (vl-catch-all-apply 'psp-page-preset (list media)))
          (if (vl-catch-all-error-p res)
            (progn
              (princ "\n  ПСП: предустановка ОШИБКА: ")
              (princ (vl-catch-all-error-message res)))
            (progn
              (setq chk (vl-catch-all-apply 'psp-get (list
                          (psp-get (psp-get (vlax-get-acad-object)
                                            'ActiveDocument) 'ActiveLayout)
                          'CanonicalMediaName)))
              (princ (strcat "\n  ПСП: предустановка: "
                             (if (and (= (type chk) 'STR) (/= chk ""))
                               chk "НЕ ПРИМЕНИЛАСЬ")))))
          ;; Окно печати задаётся в UCS
          (setq x1 (car (trans (list (nth 4 it) (nth 5 it)) 0 1))
                y1 (cadr (trans (list (nth 4 it) (nth 5 it)) 0 1))
                x2 (car (trans (list (nth 6 it) (nth 7 it)) 0 1))
                y2 (cadr (trans (list (nth 6 it) (nth 7 it)) 0 1)))
          (setq *psp-stage* "печать листа")
          (setq res (vl-catch-all-apply 'psp-plot-tape
                      (list (strcat fname ".pdf") media rot-str ctb
                            x1 y1 x2 y2 chk nil)))
          (psp-page-restore)
          ;; Если -ПЕЧАТЬ застряла на незапланированном вопросе, в стеке
          ;; остаётся CMDACTIVE; его остатки сдвинули бы следующую ленту.
          ;; Снимаем по ESC (без пустых Enter) и пропускаем лист.
          (if (> (getvar "CMDACTIVE") 0)
            (progn
              (princ "\n  ПСП: -ПЕЧАТЬ застряла на вопросе, снимаю по ESC.")
              (princ "\n  ПСП: для диагностики включите ПСПЭХОВКЛ и повторите.")
              (psp-clear-stuck))
            (if (vl-catch-all-error-p res)
              (princ "  ошибка печати, см. ниже")
              (princ "  отправлено на печать.")))
          ;; Вторая попытка ТОЛЬКО для листа: если PDF не появился,
          ;; значит лист был «грязный» и -ПЕЧАТЬ задала лишний вопрос
          ;; («записать изменения в макет») — повтор с 4-м «Нет».
          (if (and (= (getvar "TILEMODE") 0)
                   (not (findfile (strcat fname ".pdf"))))
            (progn
              (princ "\n  ПСП: PDF не появился — вторая попытка (плюс «Нет» на «записать изменения»).")
              (vl-catch-all-apply 'psp-page-preset (list media))
              (setq res (vl-catch-all-apply 'psp-plot-tape
                          (list (strcat fname ".pdf") media rot-str ctb
                                x1 y1 x2 y2 chk T)))
              (psp-page-restore)
              (if (> (getvar "CMDACTIVE") 0) (psp-clear-stuck))))
          (if (and (vl-catch-all-error-p res)
                   (= (getvar "CMDACTIVE") 0))
            (progn
              (princ (strcat "\nПСП: ОШИБКА [этап: " *psp-stage*
                             "] — " (vl-catch-all-error-message res)))
              (setq skip (cons (car nm-n) skip)))
            (if (findfile (strcat fname ".pdf"))
              (setq ok-list
                    (cons (list (car nm-n) (nth 2 it) (nth 3 it) media)
                          ok-list)
                    merge-list (cons (strcat (car nm-n) ".pdf")
                                     merge-list))
              (progn
                (princ (strcat "\n  ПСП: PDF не найден, ожидался: "
                               fname ".pdf"))
                (setq skip (cons (car nm-n) skip)))))
          (setq j (1+ j)))
        ;; Восстановление системных переменных
        (if has-trans (setvar "PLOTTRANSPARENCYOVERRIDE" old-trans))
        (setvar "BACKGROUNDPLOT" old-bg)
        (if (not (vl-catch-all-error-p old-paper))
          (setvar "PAPERUPDATE" old-paper))
        ;; Отчёт
        (setq ok-list (reverse ok-list))
        (princ (strcat "\nСборка: " dir))
        (princ "\n  | файл   | формат СПДС | лист | бумага PDF    |")
        (princ "\n  |--------|-------------|------|---------------|")
        (foreach row ok-list
          (princ (strcat "\n  | "
                         (psp-pad-right (nth 0 row) 6)
                         " | "
                         (psp-pad-right (if (nth 1 row) (nth 1 row) "-") 11)
                         " | "
                         (if (< (nth 2 row) 9999) (psp-num-str (nth 2 row)) "-")
                         "    | "
                         (psp-pad-right (nth 3 row) 13)
                         " |")))
        (princ (strcat "\nГотово: " (itoa (length ok-list))
                       " из " (itoa (length items))
                       "; без габаритов/ошибок: " (itoa (length skip))))
        ;; Сборка в один многостраничный PDF (если есть Ghostscript
        ;; и напечатано больше одного листа)
        (setq gs (if (> (length ok-list) 1)
                   (vl-catch-all-apply 'psp-find-gs nil)))
        (if (vl-catch-all-error-p gs)
          (progn
            (princ "\nПСП: поиск Ghostscript ОШИБКА: ")
            (princ (vl-catch-all-error-message gs))
            (setq gs nil)))
        (setq auto-merge (> (length ok-list) *psp-auto-merge-n*))
        (if (and (> (length ok-list) 1) gs)
          (progn
            (if auto-merge
              (progn
                (setq ans "Да")
                (princ (strcat "\nПСП: листов " (itoa (length ok-list))
                               " (>3) — собираю в один PDF автоматически.")))
              (progn
                (initget "Да Нет _ Yes No")
                (setq ans (getkword "\nСобрать все листы в один PDF? [Да/Нет] <Да>: "))
                (if (null ans) (setq ans "Да"))))
            (if (member (strcase ans)
                        (list (strcase "Да") (strcase "Yes")))
              (progn
                ;; полные пути: gs ищет входные файлы в СВОЁМ рабочем
                ;; каталоге, голые имена не находит (пустая страница)
                (setq pdfs (mapcar
                             '(lambda (f) (strcat dir "\\" f))
                             (reverse merge-list))
                      merged (strcat dir "\\" dwgn "_"
                                     (substr stamp 1 8) "_"
                                     (substr stamp 10 6) ".pdf"))
                (princ (strcat "\nПСП: склеиваю " (itoa (length pdfs))
                               " листов (Ghostscript)..."))
                (princ (strcat "\n  gs=" (psp-s->str gs)))
                (princ (strcat "\n  out=" (psp-s->str merged)))
                (setq res (vl-catch-all-apply
                            'psp-merge-pdfs (list gs pdfs merged)))
                (cond
                  ((vl-catch-all-error-p res)
                   (princ "\nПСП: склейка ОШИБКА: ")
                   (princ (vl-catch-all-error-message res)))
                  ((null res)
                   (princ (strcat "\nПСП: файл не появился за 20 с — "
                                  "проверьте gs вручную: " (psp-s->str gs))))
                  (t
                   (princ (strcat "\nСобрано в один PDF: " (psp-s->str res)))
(if *psp-open-res*
                     (progn
                       (princ "\nПСП: открываю в просмотрщике PDF...")
                       (if *psp-del-singles*
                         (princ (strcat "\nПСП: одиночные листы удаляются ("
                                        (itoa (length pdfs)) " шт.)")))
                       (psp-open-pdf (psp-s->str res) dir))))))
              (progn
                (princ "\nПСП: сборка в один PDF пропущена.")
                (if *psp-open-res*
                  (progn
                    (princ (strcat "\nПСП: открываю одиночные листы ("
                                   (itoa (length merge-list))
                                   " шт.) через ~" (itoa *psp-open-delay-s*) " с"))
                    (startapp "cmd.exe"
                              (strcat "/c ping -n "
                                      (itoa (1+ *psp-open-delay-s*))
                                      " 127.0.0.1 > nul"
                                      (apply 'strcat
                                             (mapcar
                                               '(lambda (f)
                                                  (strcat " & start \"\" \""
                                                          dir "\\" f "\""))
                                               (reverse merge-list))))))))))
          (if (> (length ok-list) 1)
            (princ "\nПСП: Ghostscript не найден — один PDF не собираю.\nПСП: установите GS или задайте путь командой ПСПГС.")))
        ;; Один лист без склейки: он и есть результат — открываем
        (if (and *psp-open-res* (= (length ok-list) 1))
          (startapp "cmd.exe"
                    (strcat "/c ping -n " (itoa (1+ *psp-open-delay-s*))
                            " 127.0.0.1 > nul & start \"\" \""
                            dir "\\" (nth 0 (car ok-list)) ".pdf\"")))
        ;; Открыть папку сборки
        (psp-sleep *psp-open-delay*)
        (psp-open dir)
        (princ)))))
  (princ))
(defun c:SPDSTOPDF () (c:ЭКССПДСВПДФ))
;; Открыть папку журналов и сборок в Проводнике
;; Чтение тайлов в callback кнопки «Применить»: после закрытия
;; диалога get_tile в ряде версий AutoCAD уже не действует
;; Список PDF-принтеров: все .pc3 из папки конфигураций плоттеров
(defun psp-pc3-list ( / d lst)
  (setq d (getenv "PrinterConfigDir"))
  (if (= (type d) 'STR)
    (progn
      (setq lst (vl-catch-all-apply
                  'vl-directory-files (list d "*.pc3" 1)))
      (if (not (listp lst)) (setq lst nil))))
  (if lst
    (setq lst (vl-sort lst
                (function (lambda (a b) (< (strcase a) (strcase b))))))
    (setq lst (list "DWG To PDF.pc3")))
  (if (not (member (strcase (if *psp-pc3* *psp-pc3* "") T)
                   (mapcar '(lambda (x) (strcase x T)) lst)))
    (setq lst (cons (if *psp-pc3* *psp-pc3* "PlotSPDSToPDF.pc3") lst)))
  lst)

;; Список CTB (стилей печати) из папки стилей AutoCAD
(defun psp-ctb-list ( / d lst cur)
  (setq d (getenv "PrinterStyleSheetDir"))
  (if (= (type d) 'STR)
    (progn
      (setq lst (vl-catch-all-apply
                  'vl-directory-files (list d "*.ctb" 1)))
      (if (not (listp lst)) (setq lst nil))))
  (if lst
    (setq lst (vl-sort lst
                (function (lambda (a b) (< (strcase a) (strcase b))))))
    (setq lst (list "monochrome.ctb" "acad.ctb")))
  (foreach cur (list (if (boundp '*pfp-ctb-mono*) *pfp-ctb-mono*)
                     (if (boundp '*pfp-ctb-color*) *pfp-ctb-color*))
    (if (and (= (type cur) 'STR) (/= cur "")
             (not (member (strcase cur T)
                          (mapcar '(lambda (x) (strcase x T)) lst))))
      (setq lst (cons cur lst))))
  lst)

;; Список СИСТЕМНЫХ принтеров Windows (для FP-модуля): ключи
;; HKLM\SYSTEM\CurrentControlSet\Control\Print\Printers;
;; FinePrint добавляется, если его нет; текущие значения тоже
(defun psp-printer-list ( / lst s cur)
  (setq lst (vl-catch-all-apply 'vl-registry-descendents
              (list "HKEY_LOCAL_MACHINE\\SYSTEM\\CurrentControlSet\\Control\\Print\\Printers")))
  (if (not (listp lst)) (setq lst nil))
  (setq s nil)
  (foreach x lst
    (if (and (= (type x) 'STR) (/= x "")
             (not (member (strcase x T) (mapcar '(lambda (y) (strcase y T)) s))))
      (setq s (cons x s))))
  (setq s (vl-sort s (function (lambda (a b) (< (strcase a) (strcase b))))))
  (if (not (member (strcase "FinePrint" T)
                   (mapcar '(lambda (y) (strcase y T)) s)))
    (setq s (cons "FinePrint" s)))
  (foreach cur (list (getcfg "AppData/PlotFrame/FPPrinterA4")
                     (getcfg "AppData/PlotFrame/FPPrinterA3"))
    (if (and (= (type cur) 'STR) (/= cur "")
             (not (member (strcase cur T)
                          (mapcar '(lambda (y) (strcase y T)) s))))
      (setq s (cons cur s))))
  (if (null s) (setq s (list "FinePrint")))
  s)

;; Заполнить выпадающий список и выбрать текущее значение
(defun psp-popup-fill (key lst cur / idx s keep)
  ;; только строки; cur через psp-s->str: ошибка типа здесь не нужна
  (setq keep nil)
  (foreach s lst
    (if (= (type s) 'STR) (setq keep (cons s keep))))
  (setq keep (reverse keep) cur (psp-s->str cur) idx 0)
  (start_list key)
  (foreach s keep (add_list s))
  (end_list)
  (while (and keep (/= (strcase (car keep) T) (strcase cur T)))
    (setq keep (cdr keep) idx (1+ idx)))
  (if (null keep) (setq idx 0))
  (set_tile key (itoa idx))
  (princ))

;; Кнопка «Обзор...»: диалог выбора папки Windows (проводник)
(defun psp-browse-folder ( / sh hw fld pth)
  (setq sh (vl-catch-all-apply
             'vlax-create-object (list "Shell.Application")))
  (if (and sh (not (vl-catch-all-error-p sh)))
    (progn
      (setq hw (vl-catch-all-apply
                 'vlax-get (list (vlax-get-acad-object) 'HWND)))
      (if (/= (type hw) 'INT) (setq hw 0))
      (setq fld (vl-catch-all-apply
                  'vlax-invoke
                  (list sh 'BrowseForFolder hw "Выберите папку для PDF" 0)))
      (if (and fld (not (vl-catch-all-error-p fld)))
        (progn
          (setq pth (vl-catch-all-apply
                      'vlax-get (list (vlax-get fld 'Self) 'Path)))
          (if (and (= (type pth) 'STR) (/= pth "") (/= ":" (substr pth 1 1)))
            (set_tile "dir" pth))
          (vl-catch-all-apply 'vlax-release-object (list fld)))))
    (princ "\nПСП: диалог папок недоступен — введите путь вручную."))
  (if (and sh (not (vl-catch-all-error-p sh)))
    (vl-catch-all-apply 'vlax-release-object (list sh)))
  (princ))

(defun psp-tiles-read ( )
  (setq *psp-t-dir*   (psp-s->str (get_tile "dir"))
        *psp-t-pc3*   (psp-str-or
                        (nth (atoi (get_tile "pc3list")) *psp-t-pc3s*)
                        (psp-str-or *psp-pc3* "PlotSPDSToPDF.pc3"))
        *psp-t-pcol*  (= (psp-s->str (get_tile "mcol")) "1")
        *psp-t-ctbm*  (psp-str-or
                        (nth (atoi (get_tile "ctbm")) *psp-t-ctbs*)
                        "monochrome.ctb")
        *psp-t-ctbc*  (psp-str-or
                        (nth (atoi (get_tile "ctbc")) *psp-t-ctbs*)
                        "acad.ctb")
        *psp-t-fpp4*  (psp-str-or
                        (nth (atoi (get_tile "fpp4")) *psp-t-fpps*)
                        "FinePrint")
        *psp-t-fpp3*  (psp-str-or
                        (nth (atoi (get_tile "fpp3")) *psp-t-fpps*)
                        "FinePrint")
        *psp-t-thr*   (atoi (psp-s->str (get_tile "thr")))
        *psp-t-delay* (atoi (psp-s->str (get_tile "delay")))
        *psp-t-openres* (= (psp-s->str (get_tile "openres")) "1")
        *psp-t-dels*    (= (psp-s->str (get_tile "dels")) "1")
        *psp-t-quality* (cond ((= (psp-s->str (get_tile "q0")) "1") 0)
                              ((= (psp-s->str (get_tile "q2")) "1") 2)
                              (t 1))
        *psp-t-pfq*     (cond ((= (psp-s->str (get_tile "rq0")) "1") 0)
                              ((= (psp-s->str (get_tile "rq2")) "1") 2)
                              (t 1)))
  (princ))

;; Диалог настроек (DCL генерируется во временную папку при вызове)
(defun psp-settings-dialog ( / f dcl d id s n res st)
  (setq dcl (strcat (getenv "TEMP") "\\PlotSPDSToPDF_settings.dcl"))
  (setq f (open dcl "w"))
  ;; v0.80: сетка — каждая строка = [текст 30, вправо][поле 30];
  ;; принтеры PDF/A4/A3 — сверху одной колонкой; цвет — пара радио
  (write-line "psp_set : dialog { label = \"Настройки печати\";" f)
  (write-line "  : boxed_column { label = \"Папка сохранения\";" f)
  (write-line "    : row {" f)
  (write-line "      : edit_box { key = \"dir\"; edit_width = 60; fixed_width = true; }" f)
  (write-line "    }" f)
  (write-line "    : row {" f)
  (write-line "      : text { label = \"(пусто = временная папка сборок)\"; }" f)
  (write-line "      : button { key = \"browse\"; label = \"Обзор...\"; width = 10; fixed_width = true; }" f)
  (write-line "    }" f)
  (write-line "  }" f)
  (write-line "  : boxed_column { label = \"Цвет и стили печати\";" f)
  (write-line "    : row {" f)
  (write-line "      : text { label = \"Принтер PDF:\"; width = 30; fixed_width = true; alignment = right; }" f)
  (write-line "      : popup_list { key = \"pc3list\"; width = 30; fixed_width = true; }" f)
  (write-line "    }" f)
  (write-line "    : row {" f)
  (write-line "      : text { label = \"Принтер A4:\"; width = 30; fixed_width = true; alignment = right; }" f)
  (write-line "      : popup_list { key = \"fpp4\"; width = 30; fixed_width = true; }" f)
  (write-line "    }" f)
  (write-line "    : row {" f)
  (write-line "      : text { label = \"Принтер A3:\"; width = 30; fixed_width = true; alignment = right; }" f)
  (write-line "      : popup_list { key = \"fpp3\"; width = 30; fixed_width = true; }" f)
  (write-line "    }" f)
  (write-line "    : radio_column {" f)
  (write-line "      : radio_button { key = \"cmb\"; label = \"Чёрно-белая печать\"; }" f)
  (write-line "      : radio_button { key = \"mcol\"; label = \"Цветная печать\"; }" f)
  (write-line "    }" f)
  (write-line "    : row {" f)
  (write-line "      : text { label = \"Чёрно-белая печать:\"; width = 30; fixed_width = true; alignment = right; }" f)
  (write-line "      : popup_list { key = \"ctbm\"; width = 30; fixed_width = true; }" f)
  (write-line "    }" f)
  (write-line "    : row {" f)
  (write-line "      : text { label = \"Цветная печать:\"; width = 30; fixed_width = true; alignment = right; }" f)
  (write-line "      : popup_list { key = \"ctbc\"; width = 30; fixed_width = true; }" f)
  (write-line "    }" f)
  (write-line "  }" f)
  (write-line "  : boxed_column { label = \"Сборка и результат\";" f)
  (write-line "    : row {" f)
  (write-line "      : text { label = \"Автосборка при листах БОЛЬШЕ:\"; width = 30; fixed_width = true; alignment = right; }" f)
  (write-line "      : edit_box { key = \"thr\"; edit_width = 30; fixed_width = true; }" f)
  (write-line "    }" f)
  (write-line "    : row {" f)
  (write-line "      : text { label = \"Задержка открытия, с:\"; width = 30; fixed_width = true; alignment = right; }" f)
  (write-line "      : edit_box { key = \"delay\"; edit_width = 30; fixed_width = true; }" f)
  (write-line "    }" f)
  (write-line "    : toggle { key = \"openres\"; label = \"Открывать результат (склейку / одиночные)\"; }" f)
  (write-line "    : toggle { key = \"dels\"; label = \"Удалять одиночные листы после склейки\"; }" f)
  (write-line "  }" f)
  (write-line "  : boxed_column { label = \"Качество печати \\\"Рамка в PDF\\\" (ЭКСВПДФ)\";" f)
  (write-line "    : radio_row {" f)
  (write-line "      : radio_button { key = \"rq0\"; label = \"Низкое (-1)\"; width = 23; fixed_width = true; }" f)
  (write-line "      : radio_button { key = \"rq1\"; label = \"Среднее\"; width = 16; fixed_width = true; }" f)
  (write-line "      : radio_button { key = \"rq2\"; label = \"Высокое (+1)\"; width = 16; fixed_width = true; }" f)
  (write-line "    }" f)
  (write-line "  }" f)
  (write-line "  : boxed_column { label = \"Качество печати \\\"Рамка СПДС в PDF\\\" (ЭКССПДСВПДФ)\";" f)
  (write-line "    : radio_row {" f)
  (write-line "      : radio_button { key = \"q0\"; label = \"Низкое (по формату)\"; width = 23; fixed_width = true; }" f)
  (write-line "      : radio_button { key = \"q1\"; label = \"Среднее (+1)\"; width = 16; fixed_width = true; }" f)
  (write-line "      : radio_button { key = \"q2\"; label = \"Высокое (+2)\"; width = 16; fixed_width = true; }" f)
  (write-line "    }" f)
  (write-line "  }" f)
  (write-line "  : row { spacer;" f)
  (write-line "    : button { key = \"ok\"; label = \"Применить\"; is_default = true; }" f)
  (write-line "    : button { key = \"cancel\"; label = \"Отмена\"; is_cancel = true; }" f)
  (write-line "    spacer; } }" f)
  (close f)
  (setq d (load_dialog dcl))
  (if (null (new_dialog "psp_set" d))
    (progn
      (unload_dialog d)
      (princ (strcat "\nПСП: диалог настроек не открылся (" dcl ").")))
    (progn
      (setq st "заполнение списков")
      (set_tile "dir" (psp-s->str (if *psp-pdf-dir* *psp-pdf-dir* "")))
      (setq *psp-t-pc3s* (psp-pc3-list))
      (psp-popup-fill "pc3list" *psp-t-pc3s* *psp-pc3*)
      (set_tile "cmb" (if *psp-color-mode* "0" "1"))
      (set_tile "mcol" (if *psp-color-mode* "1" "0"))
      (setq *psp-t-ctbs* (psp-ctb-list))
      (psp-popup-fill "ctbm" *psp-t-ctbs*
        (if *psp-ctb-mono* *psp-ctb-mono* "monochrome.ctb"))
      (psp-popup-fill "ctbc" *psp-t-ctbs*
        (if *psp-ctb-color* *psp-ctb-color* "acad.ctb"))
      (setq *psp-t-fpps* (psp-printer-list))
      (setq s (getcfg "AppData/PlotFrame/FPPrinterA4"))
      (psp-popup-fill "fpp4" *psp-t-fpps*
        (if (and (= (type s) 'STR) (/= s "")) s "FinePrint"))
      (setq s (getcfg "AppData/PlotFrame/FPPrinterA3"))
      (psp-popup-fill "fpp3" *psp-t-fpps*
        (if (and (= (type s) 'STR) (/= s "")) s "FinePrint"))
      (set_tile "thr" (itoa *psp-auto-merge-n*))
      (set_tile "delay" (itoa *psp-open-delay-s*))
      (set_tile "openres" (if *psp-open-res* "1" "0"))
      (set_tile "dels" (if *psp-del-singles* "1" "0"))
      (set_tile "q0" (if (= *psp-quality* 0) "1" "0"))
      (set_tile "q1" (if (= *psp-quality* 1) "1" "0"))
      (set_tile "q2" (if (= *psp-quality* 2) "1" "0"))
      (setq s (getcfg "AppData/PlotFrame/Quality"))
      (setq n (if (= (type s) 'STR) (atoi s) 1))
      (if (not (and (>= n 0) (<= n 2))) (setq n 1))
      (set_tile "rq0" (if (= n 0) "1" "0"))
      (set_tile "rq1" (if (= n 1) "1" "0"))
      (set_tile "rq2" (if (= n 2) "1" "0"))
      (mode_tile "dir" 2)
      (action_tile "browse" "(psp-browse-folder)")
      (action_tile "ok" "(psp-tiles-read)(done_dialog 1)")
      ;; Всё вплоть до конца Apply — под страховкой: ошибка НЕ долж-
      ;; на оставлять диалог открытым (живой диалог блокирует -ПЕЧАТЬ)
      (setq res (vl-catch-all-apply
                  '(lambda ( )
                     (progn
      (setq st "диалог")
      (setq id (start_dialog))
      (setq st "сохранение настроек")
      (if (= id 1)
        (progn
          (setq s *psp-t-dir*)
          (while (and (> (strlen s) 0) (= (substr s (strlen s) 1) "\\"))
            (setq s (substr s 1 (1- (strlen s)))))
          (setq *psp-pdf-dir* s *psp-output-dir* (if (/= s "") s nil))
          (setcfg "AppData/PlotSPDS/PDFDir" s)
          (setcfg "AppData/PlotFrame/OutDir" s)
          (if (boundp 'c:ЭКСВПДФ)
            (setq *pfp-output-dir* (if (/= s "") s nil)))
          (setq s (psp-s->str *psp-t-pc3*))
          (if (not (wcmatch (strcase s T) "*`.pc3"))
            (setq s "PlotSPDSToPDF.pc3"))
          (setq *psp-pc3* s)
          (setcfg "AppData/PlotSPDS/PC3" s)
          ;; Параметры печати базы (задача 12): цвет + CTB
          (setcfg "AppData/PlotFrame/ColorMode"
                  (if *psp-t-pcol* "1" "0"))
          (setcfg "AppData/PlotFrame/CtbMono" (psp-s->str *psp-t-ctbm*))
          (setcfg "AppData/PlotFrame/CtbColor" (psp-s->str *psp-t-ctbc*))
          ;; Принтеры FP-модуля (ЭКСВПФПА4 / ЭКСВПФПА3)
          (setcfg "AppData/PlotFrame/FPPrinterA4"
                  (psp-s->str *psp-t-fpp4*))
          (setcfg "AppData/PlotFrame/FPPrinterA3"
                  (psp-s->str *psp-t-fpp3*))
          ;; СПДС печатает по *psp-*, база — по *pfp-*: применяем к обоим
          (setq *psp-color-mode* *psp-t-pcol*
                *psp-ctb-mono* *psp-t-ctbm*
                *psp-ctb-color* *psp-t-ctbc*)
          (if (boundp 'c:ЭКСВПДФ)
            (progn
              (setq *pfp-color-mode* *psp-t-pcol*)
              (setq *pfp-ctb-mono* *psp-t-ctbm*)
              (setq *pfp-ctb-color* *psp-t-ctbc*)))
          (setq n *psp-t-thr*)
          (if (< n 1) (setq n 1))
          (setq *psp-auto-merge-n* n)
          (setcfg "AppData/PlotSPDS/AutoMergeN" (itoa n))
          (setq n *psp-t-delay*)
          (if (< n 0) (setq n 0))
          (setq *psp-open-delay-s* n)
          (setcfg "AppData/PlotSPDS/OpenDelay" (itoa n))
          (setq *psp-open-res* *psp-t-openres*)
          (setcfg "AppData/PlotSPDS/OpenRes" (if *psp-open-res* "1" "0"))
          (setq *psp-del-singles* *psp-t-dels*)
          (setcfg "AppData/PlotSPDS/DelSingles" (if *psp-del-singles* "1" "0"))
          (setq *psp-quality* *psp-t-quality*)
          (setcfg "AppData/PlotSPDS/Quality" (itoa *psp-quality*))
          (setcfg "AppData/PlotFrame/Quality" (itoa *psp-t-pfq*))
          (if (boundp 'c:ЭКСВПДФ)
            (setq *pfp-quality* *psp-t-pfq*))
          (princ "\nПСП: настройки сохранены. Применено:")
          (princ "\n  +-----------------------------+-----------------------------------+")
          (princ (strcat "\n  | " (psp-pad-right "параметр" 28)
                          "| " (psp-pad-right "значение" 34) "|"))
          (princ "\n  +-----------------------------+-----------------------------------+")
          (defun psp-row (n v)
            (princ (strcat "\n  | " (psp-pad-right n 28)
                           "| " (psp-pad-right (psp-s->str v) 34) "|")))
          (psp-row "папка сохранения"
                   (if (= *psp-pdf-dir* "")
                     "%TEMP%\\PlotFramePDF" *psp-pdf-dir*))
          (psp-row "PDF-принтер (СПДС)" *psp-pc3*)
          (psp-row "цвет печати"
                   (if *psp-color-mode* "цвет" "ч/б"))
          (psp-row "Чёрно-белая печать (CTB)" *psp-ctb-mono*)
          (psp-row "Цветная печать (CTB)" *psp-ctb-color*)
          (psp-row "принтер для A4 (FP)" *psp-t-fpp4*)
          (psp-row "принтер для A3 (FP)" *psp-t-fpp3*)
          (psp-row "автосборка в один PDF"
                   (strcat "при листах > " (itoa *psp-auto-merge-n*)))
          (psp-row "задержка открытия"
                   (strcat (itoa *psp-open-delay-s*) " с"))
          (psp-row "открывать результат"
                   (if *psp-open-res* "да" "нет"))
          (psp-row "удалять одиночные листы"
                   (if *psp-del-singles* "да" "нет"))
          (psp-row "качество СПДС"
                   (nth *psp-quality*
                        (list "Низкое" "Среднее" "Высокое")))
          (psp-row "качество рамки"
                   (nth *psp-t-pfq*
                        (list "Низкое" "Среднее" "Высокое")))
          (princ "\n  +-----------------------------+-----------------------------------+")
          ))))))))
      (unload_dialog d)
      (if (vl-catch-all-error-p res)
        (progn
          (princ (strcat "\nПСП: ошибка диалога настроек [этап: "
                         (psp-s->str st) "]: "))
          (princ (vl-catch-all-error-message res))))
  (princ))

(defun c:ПСПНАСТРОЙКИ () (psp-settings-dialog))
(defun c:PSPSET () (c:ПСПНАСТРОЙКИ))

;; Качество печати SPDS: 0 = формат в формат, 1 = +1, 2 = +2
(defun c:ПСПКАЧ ( / s names)
  (setq names (list "Низкое (формат в формат)"
                    "Среднее (+1 формат)"
                    "Высокое (+2 формата)"))
  (initget "Низкое Среднее Высокое _ Low Med High")
  (setq s (getkword (strcat "\nКачество печати [Низкое/Среднее/Высокое] <"
                            (nth *psp-quality*
                                 (list "Низкое" "Среднее" "Высокое"))
                            ">: ")))
  (cond
    ((null s))                                   ; Enter — оставить
    ((member (strcase s)
             (list (strcase "Низкое") (strcase "Low"))) (setq *psp-quality* 0))
    ((member (strcase s)
             (list (strcase "Высокое") (strcase "High"))) (setq *psp-quality* 2))
    (t (setq *psp-quality* 1)))
  (setcfg "AppData/PlotSPDS/Quality" (itoa *psp-quality*))
  (princ (strcat "\nПСП: качество печати — " (nth *psp-quality* names) "."))
  (princ))
(defun c:PSPQUAL () (c:ПСПКАЧ))

;; Справка: команды и однократная настройка «тихого» PDF-принтера
(defun c:ПСППОМОЩЬ ( )
  (princ (strcat "\nPlotSPDSToPDF v" *psp-ver* " — экспорт форматов СПДС в PDF."))
  (princ "\nКоманды: ЭКССПДСВПДФ (SPDSTOPDF) — экспорт; ПСПНАСТРОЙКИ (PSPSET) —")
  (princ "\n  настройки (папка PDF, автосборка, задержка, принтер, удаление);")
  (princ "\n  ПСППАПКА (PSPPAPKA) — папка сборок; ПСПГС (PSPGS) — путь к Ghostscript;")
  (princ "\n  страховой поиск: <диск>:\\PlotFrameToPDF\\gs\\bin (C:/D:/E:) — портативный gs.")
  (princ "\n  ПСПЭХОВКЛ/ПСПЭХОВЫКЛ — эхо ленты -ПЕЧАТЬ; ПСППОМОЩЬ (PSPHELP) — справка.")
  (princ "\nКачество печати: ПСПКАЧ (PSPQUAL) — Низкое=формат-в-формат,")
  (princ "\n  Среднее=+1 формат, Высокое=+2 формата; также в ПСПНАСТРОЙКИ.")
  (princ "\nКачество базы (ЭКСВПДФ) — нижняя радиострока в ПСПНАСТРОЙКИ.")
  (princ "\nПорядок листов: по номеру (15, 15.1, 15.2...), «0» — титульный, первым.")
  (princ "\nБольше трёх листов — сборка в один PDF автоматически;")
  (princ "\n  открывается ТОЛЬКО склейка, одиночные листы не запускаются")
  (princ "\n  и удаляются (повторные попытки ~1 мин — просмотрщик держит файлы).")
  (princ "\nОДНОКРАТНАЯ НАСТРОЙКА «тихого» принтера (если AutoCAD сам")
  (princ "\nоткрывает каждый отпечатанный лист):")
  (princ "\n  1) открыть папку принтеров: в консоли AutoCAD —")
  (princ "\n       (startapp \"explorer.exe\" (getenv \"PrinterConfigDir\"))")
  (princ "\n     (команда ПЛОТТЕРМАНАДЖЕР может не открываться — не страшно)")
  (princ "\n  2) копия DWG To PDF.pc3 -> переименовать в PlotSPDSToPDF.pc3")
  (princ "\n  3) двойной клик по копии -> «Пользовательские свойства...» ->")
  (princ "\n     снять флажок «Показывать результаты в программе просмотра» -> OK")
  (princ "\n  4) в модуле имя уже задано по умолчанию; после загрузки можно")
  (princ "\n     переопределить: (setq *psp-pc3* \"PlotSPDSToPDF.pc3\")")
  (princ "\n  Если копии нет, экспорт падает с «устройство не найдено» — тогда")
  (princ "\n  (setq *psp-pc3* \"DWG To PDF.pc3\") после загрузки.")
  (princ))

(defun c:PSPPOMOSH () (c:ПСППОМОЩЬ))
(defun c:PSPHELP () (c:ПСППОМОЩЬ))

(defun c:ПСППАПКА ( / d)
  (setq d (psp-output-dir))
  (if (vl-file-directory-p d)
    (progn
      (startapp "explorer.exe" d)
      (princ (strcat "\nПСП: папка открыта — " d)))
    (princ (strcat "\nПСП: папка не существует — " d)))
  (princ))
(defun c:PSPPAPKA () (c:ПСППАПКА))

;; Диагностика: показывать/скрывать все подсказки -ПЕЧАТЬ во время
;; серийной печати (эхо команд в консоль)
(defun psp-echo-set (v)
  (setq *psp-plot-echo* v)
  (princ (if v
    "\nПСП: эхо печати ВКЛЮЧЕНО — подсказки -ПЕЧАТЬ будут видны."
    "\nПСП: эхо печати выключено."))
  (princ))
(defun c:ПСПЭХОВКЛ () (psp-echo-set T))
(defun c:ПСПЭХОВЫКЛ () (psp-echo-set nil))
(defun c:PSPECHOON () (psp-echo-set T))
(defun c:PSPECHOOFF () (psp-echo-set nil))

;; Переключение ленты -ПЕЧАТЬ: с ответом на «Масштабировать веса
;; линий?» или без (зависит от сборки AutoCAD)
(defun c:ПСПЛЕНТА ( )
  (setq *psp-tape-mode* (not *psp-tape-mode*))
  (princ (if *psp-tape-mode*
    "\nПСП: лента с ответом «Масштабировать веса линий?»."
    "\nПСП: лента без ответа «Масштабировать веса линий?» (как в транскрипте 0.24)."))
  (princ))
(defun c:PSPTAPE () (c:ПСПЛЕНТА))

;; Задать путь к Ghostscript вручную и запомнить его постоянно
(defun c:ПСПГС ( / p)
  (setq p (getstring T
    "\nПолный путь к gswin64c.exe (Enter — очистить): "))
  (if (= p "")
    (progn
      (setq *psp-gs* nil)
      (setcfg "AppData/PlotSPDS/GS" "")
      (princ "\nПСП: путь к Ghostscript очищен, поиск автоматический."))
    (progn
      (setq p (vl-string-trim " \"" p))
      (setq *psp-gs* p)
      (setcfg "AppData/PlotSPDS/GS" p)
      (princ (strcat "\nПСП: Ghostscript: " p
                     "\nПСП: если склейка не соберётся — проверьте путь."))))
  (princ))
(defun c:PSPGS () (c:ПСПГС))
;; ---------------------------------------------------------------------------
;; Загрузка
;; ---------------------------------------------------------------------------

(princ (strcat "\nЗагружено: PlotSPDSToPDF.lsp v" *psp-ver*
               " — команды: ЭКССПДСВПДФ / SPDSTOPDF, ПСППАПКА / PSPPAPKA,"))
(princ (strcat "\nПринтер: " *psp-pc3*
               "; если листы сами открываются — см. ПСППОМОЩЬ / PSPHELP."))
(princ "\nДиагностика ЭКССПДСДИАГ — в PlotSPDSDiag.lsp: загрузите его следом,")
(princ "\nзатем выполните ЭКССПДСДИАГ и пришлите вывод и spds_diag.txt.")
(princ)
