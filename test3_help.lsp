(defun c:ПСППОМОЩЬ ( )
  (princ (strcat "\nPlotSPDSToPDF v" *psp-ver* " — экспорт форматов СПДС в PDF."))
  (princ "\nКоманды: ЭКССПДСВПДФ (SPDSTOPDF) — экспорт; ПСПНАСТРОЙКИ (PSPSET) —")
  (princ "\n  настройки (папка PDF, автосборка, задержка, принтер, удаление);")
  (princ "\n  ПСППАПКА (PSPPAPKA) — папка сборок; ПСПГС (PSPGS) — путь к Ghostscript;")
  (princ "\n  ПСПЭХОВКЛ/ПСПЭХОВЫКЛ — эхо ленты -ПЕЧАТЬ; ПСППОМОЩЬ (PSPHELP) — справка.")
  (princ "\nПорядок листов: по номеру (15, 15.1, 15.2...), «0» — титульный, первым.")
  (princ "\nБольше трёх листов — сборка в один PDF автоматически;")
  (princ "\n  открывается ТОЛЬКО склейка, одиночные листы не запускаются")
  (princ "\n  и удаляются (повторные попытки ~1 мин — просмотрщик держит файлы).")
  (princ "\nОДНОКРАТНАЯ НАСТРОЙКА «тихого» принтера (если AutoCAD сам")
  (princ "\nоткрывает каждый отпечатанный лист):")
  (princ "\n  1) открыть папку принтеров: в консоли AutoCAD —")
  (princ "\n       (startapp \"explorer.exe\" (getenv \"PrinterConfigDir\"))")
  (princ "\n     (команда ПЛОТТЕРМАНАДЖЕР может не открываться — не страшно)")
  (princ "\n  2) копия DWG To PDF.pc3 -> переименовать в PlotSPDSToPDF.pc3")
  (princ "\n  3) двойной клик по копии -> «Пользовательские свойства...» ->")
  (princ "\n     снять флажок «Показывать результаты в программе просмотра» -> OK")
  (princ "\n  4) в модуле имя уже задано по умолчанию; после загрузки можно")
  (princ "\n     переопределить: (setq *psp-pc3* \"PlotSPDSToPDF.pc3\")")
  (princ "\n  Если копии нет, экспорт падает с «устройство не найдено» — тогда")
  (princ "\n  (setq *psp-pc3* \"DWG To PDF.pc3\") после загрузки.")
  (princ))
(defun c:PSPPOMOSH () (c:ПСППОМОЩЬ))
(defun c:PSPHELP () (c:ПСППОМОЩЬ))
(princ "\nT3-OK")(princ)
