(defun psp-settings-dialog ( / f dcl d id s n)
  (setq dcl (strcat (getenv "TEMP") "\\PlotSPDSToPDF_settings.dcl"))
  (setq f (open dcl "w"))
  (write-line "psp_set : dialog { label = \"PlotSPDSToPDF — настройки\";" f)
  (write-line "  : edit_box { key = \"dir\"; label = \"Папка сохранения PDF:\"; edit_width = 48; }" f)
  (write-line "  : text { label = \"   (пусто = временная папка сборок)\"; }" f)
  (write-line "  : edit_box { key = \"pc3\"; label = \"PDF-принтер (pc3):\"; edit_width = 34; }" f)
  (write-line "  : edit_box { key = \"thr\"; label = \"Автосборка при листах БОЛЬШЕ:\"; edit_width = 5; }" f)
  (write-line "  : edit_box { key = \"delay\"; label = \"Задержка открытия, с:\"; edit_width = 5; }" f)
  (write-line "  : toggle { key = \"openres\"; label = \"Открывать результат (склейку / одиночные)\"; }" f)
  (write-line "  : toggle { key = \"dels\"; label = \"Удалять одиночные листы после склейки\"; }" f)
  (write-line "  : row { spacer { width = 1; }" f)
  (write-line "    : button { key = \"ok\"; label = \"Применить\"; is_default = true; }" f)
  (write-line "    : button { key = \"cancel\"; label = \"Отмена\"; is_cancel = true; }" f)
  (write-line "    spacer { width = 1; } } }" f)
  (close f)
  (setq d (load_dialog dcl))
  (princ "\nT7-OK")(princ))
(princ)
