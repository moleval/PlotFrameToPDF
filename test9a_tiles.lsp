(defun psp-t9a ( / dcl d)
  (setq dcl (strcat (getenv "TEMP") "\\PlotSPDSToPDF_settings.dcl"))
  (setq d (load_dialog dcl))
  (if (null (new_dialog "psp_set" d))
    (progn (unload_dialog d) (princ "\nT9a: dialog not opened"))
    (progn
      (set_tile "dir" "")
      (set_tile "pc3" "")
      (set_tile "thr" "3")
      (set_tile "delay" "5")
      (set_tile "openres" "1")
      (set_tile "dels" "1")
      (mode_tile "dir" 2)
      (action_tile "ok" "(done_dialog 1)")
      (setq d (start_dialog))
      (unload_dialog d)
      (princ "\nT9a-OK")))
  (princ))
(princ)
