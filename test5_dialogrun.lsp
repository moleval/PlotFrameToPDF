(defun psp-settings-dialog ( / dcl d id s n)
  (setq dcl (strcat (getenv "TEMP") "\\PlotSPDSToPDF_settings.dcl"))
  (setq d (load_dialog dcl))
  (if (null (new_dialog "psp_set" d))
    (progn
      (unload_dialog d)
      (princ (strcat "\nПСП: диалог настроек не открылся (" dcl ").")))
    (progn
      (set_tile "dir" (if *psp-pdf-dir* *psp-pdf-dir* ""))
      (set_tile "pc3" *psp-pc3*)
      (set_tile "thr" (itoa *psp-auto-merge-n*))
      (set_tile "delay" (itoa *psp-open-delay-s*))
      (set_tile "openres" (if *psp-open-res* "1" "0"))
      (set_tile "dels" (if *psp-del-singles* "1" "0"))
      (mode_tile "dir" 2)
      (action_tile "ok" "(done_dialog 1)")
      (setq id (start_dialog))
      (unload_dialog d)
      (if (= id 1)
        (progn
          (setq s (get_tile "dir"))
          (while (and (> (strlen s) 0) (= (substr s (strlen s) 1) "\\"))
            (setq s (substr s 1 (1- (strlen s)))))
          (setq *psp-pdf-dir* s)
          (setcfg "AppData/PlotSPDS/PDFDir" s)
          (setq s (get_tile "pc3"))
          (if (= s "") (setq s "PlotSPDSToPDF.pc3"))
          (setq *psp-pc3* s)
          (setcfg "AppData/PlotSPDS/PC3" s)
          (setq n (atoi (get_tile "thr")))
          (if (< n 1) (setq n 1))
          (setq *psp-auto-merge-n* n)
          (setcfg "AppData/PlotSPDS/AutoMergeN" (itoa n))
          (setq n (atoi (get_tile "delay")))
          (if (< n 0) (setq n 0))
          (setq *psp-open-delay-s* n)
          (setcfg "AppData/PlotSPDS/OpenDelay" (itoa n))
          (setq *psp-open-res* (= (get_tile "openres") "1"))
          (setcfg "AppData/PlotSPDS/OpenRes" (if *psp-open-res* "1" "0"))
          (setq *psp-del-singles* (= (get_tile "dels") "1"))
          (setcfg "AppData/PlotSPDS/DelSingles" (if *psp-del-singles* "1" "0"))
          (princ "\nПСП: настройки сохранены."))))
(princ "\nT5-OK")(princ))
